module sonic-pon {
  namespace "http://github.com/sonic-net/sonic-pon";
  prefix sp;
  yang-version 1.1;

  import ietf-yang-types {
    prefix yang;
  }
  import sonic-pon-types {
    prefix spt;
  }
  import sonic-port {
    prefix sport;
  }
  import sonic-pon-omci-types {
    prefix omci-types;
  }

  organization
    "SONiC";
  contact
    "SONiC";
  description
    "Sonic PON YANG module covering PON configuration and state.";

  container sonic-pon {
    description
      "Top-level container for all SONIC PON.";
    container PON_CONTROLLER {
      description
        "PON_CONTROLLER table in ConfigDB.";
      list PON_CONTROLLER_LIST {
        key "controller-name";
        description
          "List of PON Controller configuration records.
           ConfigDB key: PON_CONTROLLER|<controller-name>.";
        leaf controller-name {
          description
            "Name identifier to reference this PON Controller.";
          type string {
            length "0..256";
          }
        }
        leaf device-id {
          type string {
            pattern '([0-9a-fA-F]{2}(:[0-9a-fA-F]{2}){5})|(Default)';
          }
          mandatory true;
          description
            "PON Controller identifier (PON Controller MAC Address or 'Default').";
        }
        leaf allow-unprovisioned-onus {
          type boolean;
          default "true";
          description
            "Allow unprovisioned ONUs to complete registration with PON Controller. When
             false, the controller only allows ONUs that have been inventoried on an OLT to complete
             registration.";
        }
        leaf olt-timeout {
          type uint32;
          default "300";
          description
            "The amount of time for OLT plug to be locked to a controller.  If an OLT plug doesn't receive OAM from the PON Controller in this time period, it will release its lock to allow another PON controller to manage it.";
        }
        leaf statistics-sample {
          type uint32;
          units "seconds";
          default "300";
          description
            "Minimum time between OLT statistic samples. After this amount of time, statistics will be gathered for the network devices.";
        }
        leaf logging-controller-console {
          type spt:logging-level;
          default "info";
          description
            "Severity level for log messages sent to the console.";
        }
        leaf logging-controller-file {
          type spt:logging-level;
          default "info";
          description
            "Severity level for log messages sent to the log file.";
        }
        leaf logging-controller-syslog {
          type spt:logging-level;
          default "info";
          description
            "Severity level for log messages sent to the Syslog.";
        }
        leaf logging-controller-database {
          type spt:logging-level;
          default "info";
          description
            "Severity level for logs messages sent to the database.";
        }
        leaf logging-olt-console {
          type spt:logging-enable;
          default "disable";
          description
            "Enable log messages to be sent to the console.";
        }
        leaf logging-olt-file {
          type spt:logging-enable;
          default "disable";
          description
            "Enable log messages to be sent to the log file.";
        }
        leaf logging-olt-syslog {
          type spt:logging-enable;
          default "disable";
          description
            "Enable log messages to be sent to the Syslog.";
        }
        leaf olt-management-interface-name {
          type string;
        }
        leaf unprovisioned-age {
          type uint32 {
            range "60..86400";
          }
          units "seconds";
          default "900";
          description
            "The amount of time an ONU will be kept in the Unprovisioned ONUs
             list, when no longer attempting registration.";
        }
      }
    }
    container PON_DOWNSTREAM_QOS_MAP_MAP {
      description
        "PON_DOWNSTREAM_QOS_MAP_MAP table in ConfigDB.";
      list PON_DOWNSTREAM_QOS_MAP_MAP_LIST {
        key "name cos";
        description
          "Mapping entry that classifies VLAN CoS bit values to a destination GPON XGEM Port (OLT-Service) offset.

           ConfigDB key: PON_DOWNSTREAM_QOS_MAP_MAP|<name>|<cos>.";
        leaf name {
          type string;
        }
        leaf cos {
          type uint8 {
            range "0..7";
          }
          description
            "VLAN CoS/Priority bit value for this classifier.";
        }
        leaf olt-service-offset {
          type uint8 {
            range "0..7";
          }
          description
            "Destination GPON XGEM Port offset that the start/end CoS values are classified to.";
        }
      }
    }
    container PON_OLT_INTF {
      description
        "PON_OLT_INTF table in ConfigDB.";
      list PON_OLT_INTF_LIST {
        key "olt-intf-name";
        description
          "List of OLT interfaces.
           ConfigDB key: PON_OLT_INTF|<olt-intf-name>";
        leaf olt-intf-name {
          description
            "Name identifier to reference this OLT interface.";
          type string {
            length "0..256";
          }
        }
        leaf device-id {
          type string {
            pattern '([0-9a-fA-F]{2}(:[0-9a-fA-F]{2}){5})|(Default)';
          }
          description
            "OLT interface identifier (OLT interface MAC Address or 'Default').";
        }
        leaf port-id {
          mandatory true;
          type leafref {
            path "/sport:sonic-port/sport:PORT/sport:PORT_LIST/sport:name";
          }
        }
        leaf pon-enable {
          type boolean;
          description
            "Enable the PON Optics on the module.";
          default "false";
        }
        leaf discovery-period {
          type uint32 {
            range "0 | 100..10000";
          }
          units "milliseconds";
          default "3000";
          description
            "Amount of time between discovery slots on the PON. A setting of '0' will disable discovery.";
        }
        leaf downstream-fec {
          type boolean;
          default "true";
          description
            "Enable Forward Error Correction in the downstream direction.";
        }
        leaf encryption {
          type spt:olt-encryption-mode;
          default "disabled";
          description
            "Enable the OLT interface for PON MAC layer encryption of data.";
        }
        leaf encryption-key-time {
          type uint16 {
            range "60..3600";
          }
          units "seconds";
          default "600";
          description
            "Time between changing encryption keys.";
        }
        leaf error-detection-maximum-hec-ratio {
          type uint8 {
            range "0..100";
          }
          units "percent";
          default "20";
          description
            "Maximum percentage of HEC errors to disable an ONU.";
        }
        leaf error-detection-minimum-hec-sample {
          type uint16 {
            range "0..1000";
          }
          units "GPON headers";
          default "100";
          description
            "Minimum number of HEC error samples to consider for error-detection-maximum-ratio.";
        }
        leaf error-detection-maximum-ratio {
          type uint8 {
            range "0..100";
          }
          units "percent";
          default "20";
          description
            "Maximum percentage of errored upstream bursts to disable an ONU.";
        }
        leaf error-detection-minimum-sample {
          type uint16 {
            range "0..1000";
          }
          units "Upstream Bursts";
          default "100";
          description
            "Minimum number of upstream bursts to consider for error-detection-maximum-ratio.";
        }
        leaf guard-time {
          type uint32 {
            range "16..1000";
          }
          units "upstream-slots(12.8ns)";
          default "64";
          description
            "Amount of dead time between upstream burst slots. The Guard Time should be enough for slot jitter and ONU laser off time.";
        }
        leaf max-frame-size {
          type uint32 {
            range "1518..9600";
          }
          units "octets";
          default "9600";
          description
            "Maximum frame size allowed at the PON receiver from DA to CRC32.";
        }
        leaf pon-id {
          type uint32;
          default "0";
          description
            "Unique 32-bit value assigned to each PON.";
        }
        leaf pon-tag {
          type string {
            length "0|16";
          }
          default "";
          description
            "PON-TAG description in burst profile message";
        }
        leaf aging-time {
          type uint16 {
            range "60..3600";
          }
          units "seconds";
          default "300";
          description
            "Dynamic MAC Address aging time. When the aging time expires, the address is removed from the Dynamic MAC learning table.";
        }
        leaf protection-hold {
          type boolean;
          default "false";
          description
            "When true, automatic protection actions on this OLT interface are held.
             This control is intended for external orchestration.
             When false, automatic protection behavior is allowed.";
        }
      }
    }
    container PON_OLT_INTF_NETWORK {
      description
        "PON_OLT_INTF_NETWORK table in ConfigDB.";
      list PON_OLT_INTF_NETWORK_LIST {
        key "olt-intf-name vlan-id";
        description
          "List of networks to pre-define.
           ConfigDB key: PON_OLT_INTF_NETWORK|<olt-intf-name>|<vlan-id>.";
        leaf olt-intf-name {
          type leafref {
            path "/sp:sonic-pon/sp:PON_OLT_INTF/sp:PON_OLT_INTF_LIST/sp:olt-intf-name";
          }
          description
            "References PON_OLT_INTF_LIST.";
        }
        leaf network-id {
          type uint16 {
            range "0..999";
          }
          description
            "Index for this entry.";
        }
        leaf learning-limit {
          type uint16 {
            range "0..2046";
          }
          default "2046";
          description
            "Dynamic MAC learning table size limit for this NNI Network. A value of '0' disables MAC Learning for this NNI Network.";
        }
        leaf flooding-gemport-id {
          type uint16 {
            range "1154..1278|1280..1534|1919..2046|5121..5374|5376..5630|5632..5886|5888..6013";
          }
          description
            "Flooding (Broadcast DA, Multicast DA, unknown DA downstream packets) XGEM Port ID (XGS mode only) to use for this network.";
        }
        leaf vlan-id {
          type uint16 {
            range "0..4095";
          }
          description
            "VLAN id used to identify packets on the NNI network";
        }
        leaf flooding-sla-profile {
          type string;
          description
            "SLA profile for the flooding link on this NNI network.";
        }
        ordered-by system;
      }
    }
    container PON_OLT_INTF_ONU {
      description
        "PON_OLT_INTF_ONU table in ConfigDB.";
      list PON_OLT_INTF_ONU_LIST {
        key "olt-intf-name onu-serial-number";
        description
          "For each ONU (defined by Vendor ID + Vendor SN) and service port on the ONU, the Allocation ID to use for the service port. Use 65535 or don't specify for automatic assignment.
           ConfigDB key: PON_OLT_INTF_ONU|<olt-intf-name>|<onu-serial-number>.";
        leaf olt-intf-name {
          type leafref {
            path "/sp:sonic-pon/sp:PON_OLT_INTF/sp:PON_OLT_INTF_LIST/sp:olt-intf-name";
          }
          description
            "References PON_OLT_INTF_LIST.";
        }
        leaf onu-serial-number {
          description
            "ONU serial number (defined by Vendor ID + Vendor SN).";
          type string {
            length "0..256";
          }
        }
        leaf onu-id {
          type uint16 {
            range "1..128";
          }
          description
            "The allocation ID, XGEM port ID, and ONU ID number assigned to this ONU to carry OMCI management messages.";
        }
        leaf disable {
          type boolean;
          default "false";
          description
            "When true, the disable serial number PLOAM message will be sent to this ONU if it tries to register.";
        }
        ordered-by system;
      }
    }
    container PON_OLT_INTF_ONU_OLT_SERVICE {
      description
        "PON_OLT_INTF_ONU_OLT_SERVICE table in ConfigDB.";
      list PON_OLT_INTF_ONU_OLT_SERVICE_LIST {
        key "olt-intf-name onu-serial-number service-port-id";
        description
          "List of OLT Service ports.
           ConfigDB key: PON_OLT_INTF_ONU_OLT_SERVICE|<olt-intf-name>|<onu-serial-number>|<service-port-id>.";
        leaf olt-intf-name {
          type leafref {
            path "/sp:sonic-pon/sp:PON_OLT_INTF/sp:PON_OLT_INTF_LIST/sp:olt-intf-name";
          }
          description
            "References PON_OLT_INTF_LIST.";
        }
        leaf onu-serial-number {
          type leafref {
            path "/sp:sonic-pon/sp:PON_OLT_INTF_ONU/sp:PON_OLT_INTF_ONU_LIST/sp:onu-serial-number";
          }
          description
            "References PON_OLT_INTF_ONU_LIST.";
        }
        leaf service-port-id {
          type uint32 {
            range "0..7";
          }
          description
            "OLT Service port number.";
        }
        leaf unicast-id {
          description
            "The Allocation ID to use for the service port. Use 65535 or don't specify
             for automatic assignment. Valid ALLOC-ID range is 1154..1534, excluding 1279.
            ";
          type uint16 {
            range "1154..1278 | 1280..1534";
          }
        }
      }
    }
    container PON_OLT_INTF_ONU_SERVICE_TCONT {
      description
        "PON_OLT_INTF_ONU_SERVICE_TCONT table in ConfigDB.";
      list PON_OLT_INTF_ONU_SERVICE_TCONT_LIST {
        key "olt-intf-name onu-serial-number olt-service-id";
        description
          "List of OLT Service ports.
           ConfigDB key: PON_OLT_INTF_ONU_SERVICE_TCONT|<olt-intf-name>|<onu-serial-number>|<olt-service-id>.";
        leaf olt-intf-name {
          type leafref {
            path "/sp:sonic-pon/sp:PON_OLT_INTF/sp:PON_OLT_INTF_LIST/sp:olt-intf-name";
          }
          description
            "References PON_OLT_INTF_LIST.";
        }
        leaf onu-serial-number {
          type leafref {
            path "/sp:sonic-pon/sp:PON_OLT_INTF_ONU/sp:PON_OLT_INTF_ONU_LIST/sp:onu-serial-number";
          }
          description
            "References PON_OLT_INTF_ONU_LIST.";
        }
        leaf olt-service-id {
          type uint32 {
            range "0..7";
          }
          description
            "OLT Service port number.";
        }
        leaf alloc-id {
          description
            "The Allocation ID to use for the service port. Use 65535 or don't specify
             for automatic assignment. Valid ALLOC-ID range is 1154..1534, excluding 1279.
            ";
          type uint16 {
            range "1154..1278 | 1280..1534";
          }
        }
      }
    }
    container PON_OLT_INTF_ONU_SERVICE_GEMPORT {
      description
        "PON_OLT_INTF_ONU_SERVICE_GEMPORT table in ConfigDB.";
      list PON_OLT_INTF_ONU_SERVICE_GEMPORT_LIST {
        key "olt-intf-name onu-serial-number olt-service-id";
        description
          "List of OLT GEM ports.
           ConfigDB key: PON_OLT_INTF_ONU_SERVICE_GEMPORT|<olt-intf-name>|<onu-serial-number>|<olt-service-id>.";
        leaf olt-intf-name {
          type leafref {
            path "/sp:sonic-pon/sp:PON_OLT_INTF/sp:PON_OLT_INTF_LIST/sp:olt-intf-name";
          }
          description
            "References PON_OLT_INTF_LIST.";
        }
        leaf onu-serial-number {
          type leafref {
            path "/sp:sonic-pon/sp:PON_OLT_INTF_ONU/sp:PON_OLT_INTF_ONU_LIST/sp:onu-serial-number";
          }
          description
            "References PON_OLT_INTF_ONU_LIST.";
        }
        leaf olt-service-id {
          type uint32 {
            range "0..7";
          }
          description
            "OLT Service port number.";
        }
        leaf gemport-id {
          description
            "GEM port ID for the service port.";
          type uint16;
        }
        leaf tcont-ref {
          description
            "References the TCONT entry associated with this GEM port.";
          type leafref {
            path "/sp:sonic-pon/sp:PON_OLT_INTF_ONU_SERVICE_TCONT/sp:PON_OLT_INTF_ONU_SERVICE_TCONT_LIST/sp:olt-service-id";
          }
        }
      }
    }
    container PON_OLT_PLUG_FW_BANK_FILE {
      description
        "PON_OLT_PLUG_FW_BANK_FILE table in ConfigDB.";
      list PON_OLT_PLUG_FW_BANK_FILE_LIST {
        key "olt-name bank-id";
        description
          "The database files to get firmware for the firmware banks on the OLT Module. The OLT module supports 4 banks of firmware. The list is ordered Bank0, Bank1, Bank2, and Bank3.
           ConfigDB key: PON_OLT_PLUG_FW_BANK_FILE|<olt-name>|<bank-id>.";
        leaf olt-name {
          type leafref {
            path "/sp:sonic-pon/sp:PON_OLT_PLUG/sp:PON_OLT_PLUG_LIST/sp:olt-name";
          }
          description
            "References PON_OLT_PLUG_LIST.";
        }
        leaf bank-id {
          type uint8 {
            range "0..3";
          }
          description
            "Index for this entry.";
        }
        leaf file {
          description
            "Name of the firmware file.";
          type string {
            length "0..256";
          }
        }
        leaf version {
          description
            "Name of the firmware file version.";
          type string {
            length "0..256";
          }
        }
        max-elements 4;
        ordered-by system;
      }
    }
    container PON_ONU_TEMPLATE_ONU {
      description
        "PON_ONU_TEMPLATE_ONU table in ConfigDB.";
      list PON_ONU_TEMPLATE_ONU_LIST {
        key "onu-template-name";
        description
          "ONU specific settings.
           ConfigDB key: PON_ONU_TEMPLATE_ONU|<onu-template-name>.";
        leaf onu-template-name {
          type string;
          description
            "References PON_ONU_TEMPLATE_LIST.";
        }
        leaf vlan-id {
          type uint16 {
            range "0..4095";
          }
          description
            "VID for service configuration.";
        }
        leaf fw-bank-ptr {
          type uint16 {
            range "0..1|65535";
          }
          default "65535";
          description
            "Current Firmware bank pointer. A value of '65535' disables ONU firmware upgrade.";
        }
        leaf service-config {
          type string {
            length "0..64";
          }
          units "'Disabled' or 'Add CTag' or 'Unmodified' or <Service Config Name>";
          default "Disabled";
          description
            "ONU Service Configuration has 3 generic built-in modes and the ability to load a service configuration from the database.
             XGS supports all 3 configurations and service configuration files.
            ";
        }
        leaf service-config-omci-stats {
          type boolean;
          default "false";
          description
            "When set to true, no OMCI PM MEs will be automatically configured by the Controller.
             The PM MEs need to be specified in the ONU's SRV-CONFIG file.";
        }
        leaf fw-upgrade-backoff-delay {
          type uint32 {
            range "1..10";
          }
          units "seconds";
          default "5";
          description
            "Time to wait before retransmitting a window.";
        }
        leaf fw-upgrade-backoff-divisor {
          type uint32 {
            range "1..2";
          }
          default "2";
          description
            "Controls the size of the send window during retransmissions. A value of '2' reduces
             the send window size by half for each retransmission. A value of '1' disables the backoff.";
        }
        leaf fw-upgrade-download-format {
          type spt:fw-download-format;
          default "baseline-omci";
          description
            "The format of OMCI the PON Controller will use to upgrade the ONU, regardless of the OMCC Version it reported.";
        }
        leaf fw-upgrade-end-download-timeout {
          type uint32 {
            range "0..600";
          }
          units "seconds";
          default "0";
          description
            "Time to wait for the final acknowledgement during firmware upgrade. Increase the value
             to allow the ONU additional time to write the firmware image to flash. The PON Controller
             automatically calculates the end-download-timeout when set to a value of zero.
            ";
        }
        leaf fw-upgrade-maximum-retries {
          type uint32 {
            range "1..10";
          }
          default "4";
          description
            "Maximum number of times a window is retransmitted before terminating the ONU
             firmware upgrade and reporting an error.
            ";
        }
        leaf fw-upgrade-maximum-window-size {
          type uint32 {
            range "16..256";
          }
          units "bytes";
          default "64";
          description
            "The maximum send window sized used for transfering firmware to the ONU.";
        }
        leaf fw-upgrade-response-timeout {
          type uint32 {
            range "3..120";
          }
          units "seconds";
          default "3";
          description
            "The time in seconds to wait for an acknowledgement from the ONU during firmware upgrade.";
        }
      }
    }
    container PON_ONU_TEMPLATE_ONU_FW_BANK_FILE {
      description
        "PON_ONU_TEMPLATE_ONU_FW_BANK_FILE table in ConfigDB.";
      list PON_ONU_TEMPLATE_ONU_FW_BANK_FILE_LIST {
        key "onu-template-name bank-id";
        description
          "XGS-PON: firmware source filenames for bank 0 (1st in list) and bank 1 if version doesn't match.

           ConfigDB key: PON_ONU_TEMPLATE_ONU_FW_BANK_FILE|<onu-template-name>|<bank-id>.";
        leaf onu-template-name {
          type leafref {
            path "/sp:sonic-pon/sp:PON_ONU_TEMPLATE_ONU/sp:PON_ONU_TEMPLATE_ONU_LIST/sp:onu-template-name";
          }
          description
            "References PON_ONU_TEMPLATE_ONU_LIST.";
        }
        leaf bank-id {
          type uint8 {
            range "0..1";
          }
          description
            "Index for this entry.";
        }
        leaf file {
          type string {
            length "0..64";
          }
          description
            "Name of the firmware file.";
        }
        leaf version {
          type string {
            length "0..64";
          }
          description
            "Version.";
        }
        max-elements 2;
        ordered-by system;
      }
    }
    container PON_ONU_TEMPLATE_OLT_SERVICE {
      description
        "PON_ONU_TEMPLATE_OLT_SERVICE table in ConfigDB.";
      list PON_ONU_TEMPLATE_OLT_SERVICE_LIST {
        key "onu-template-name olt-service-id";
        description
          "OLT Configuration for the services. 0 to 7 services can be configured. A service is an XGEM Port ID/Alloc ID in XGS-PON.
           ConfigDB key: PON_ONU_TEMPLATE_OLT_SERVICE|<onu-template-name>|<olt-service-id>.";
        leaf onu-template-name {
          type string;
        }
        leaf olt-service-id {
          type uint32 {
            range "0..7";
          }
          description
            "OLT Service Port number.";
        }
        leaf downstream-qos-map {
          type string {
            length "0..64";
          }
          default "";
          description
            "Reference to a Downstream QoS Map. Used with multiple XGem configurations.";
        }
        leaf enable {
          type boolean;
          default "false";
          description
            "True to enable this service port.  False to disable it.";
        }
        leaf learning-limit {
          type uint16 {
            range "0..2046";
          }
          default "2046";
          description
            "Dynamic MAC learning table size limit for this service port. A value of '0' disables MAC Learning for this service.";
        }
        leaf sla-profile {
          type string {
            length "0..64";
          }
          default "Max";
          description
            "Service level agreements for the service flow.";
        }
        leaf tcont-service-ref {
          type string {
            pattern "none|[0-7]";
          }
          description
            "none - OLT Service Port operates as a TCONT + XGem Port.
             TCONT OLT Service Port reference used to configure multiple XGem Ports for
             a single TCONT. When the value is set to a 'none', this OLT Service port operates as a
             TCONT + XGem Port. When the value references another OLT Service Port 0..7, this
             OLT Service port operates as an XGem Port only. When operating as an XGem only, this value
             must reference another OLT Service Port operating in TCONT + XGem mode.
            ";
        }
        max-elements 8;
        ordered-by system;
      }
    }
    container PON_ONU_TEMPLATE_OLT_SERVICE_NETWORK {
      description
        "PON_ONU_TEMPLATE_OLT_SERVICE_NETWORK table in ConfigDB.";
      list PON_ONU_TEMPLATE_OLT_SERVICE_NETWORK_LIST {
        key "onu-template-name olt-service-id vlan-id";
        description
          "List of VLAN network(s) (NNI and PON) through the service flow. VLAN Networks are defined by the SVLAN VID and two CVLAN VIDs.
           ConfigDB key: PON_ONU_TEMPLATE_OLT_SERVICE_NETWORK|<onu-template-name>|<olt-service-id>|<vlan-id>.";
        leaf onu-template-name {
          type string;
        }
        leaf olt-service-id {
          type leafref {
            path "/sp:sonic-pon/sp:PON_ONU_TEMPLATE_OLT_SERVICE/sp:PON_ONU_TEMPLATE_OLT_SERVICE_LIST/sp:olt-service-id";
          }
          description
            "References PON_ONU_TEMPLATE_OLT_SERVICE_LIST.";
        }
        leaf network-id {
          type uint16 {
            range "0..999";
          }
          description
            "Index for this entry.";
        }
        leaf vlan-id {
          type uint16 {
            range "0..4095";
          }
          description
            "VID service configuration.";
        }
        max-elements 1000;
        ordered-by system;
      }
    }
    container PON_ONU_TEMPLATE_SERVICE_CONFIG_VALUE {
      description
        "PON_ONU_TEMPLATE_SERVICE_CONFIG_VALUE table in ConfigDB.";
      list PON_ONU_TEMPLATE_SERVICE_CONFIG_VALUE_LIST {
        key "onu-template-name cfg-name";
        description
          "Service configuration file parameter 'onu-template-name' = 'value' pairs.
           ConfigDB key: PON_ONU_TEMPLATE_SERVICE_CONFIG_VALUE|<onu-template-name>|<cfg-name>.";
        leaf onu-template-name {
          type string;
        }
        leaf cfg-name {
          type spt:pon-string64nz;
          description
            "Name of the service configuration parameter (e.g., 'CVID UNI').";
        }
        leaf value {
          type union {
            type uint32;
            type string {
              length "0..64";
            }
          }
          mandatory true;
          description
            "Service configuration parameter value.";
        }
        leaf value-type {
          type spt:service-config-value-type;
          must ". = 'int32' or . = 'string'";
          default "int32";
          description
            "Defines the data type for the 'value' attribute.";
        }
      }
    }
    container PON_ONU_TEMPLATE_UNI {
      description
        "PON_ONU_TEMPLATE_UNI table in ConfigDB.";
      list PON_ONU_TEMPLATE_UNI_LIST {
        key "onu-template-name port-id";
        description
          "Configurations for the UNI ports on the ONU.
           ConfigDB key: PON_ONU_TEMPLATE_UNI|<onu-template-name>|<port-id>.";
        leaf onu-template-name {
          type string;
        }
        leaf port-id {
          type string {
            pattern 'UNI-ETH\s[1-9][0-9]?';
          }
          description
            "Identifier for this UNI port.";
        }
        leaf duplex {
          type spt:duplex-mode;
          default "auto";
          description
            "Sets the duplex for the Ethernet port.";
        }
        leaf enable {
          type boolean;
          description
            "Admin enable or disable for the UNI port.";
        }
        leaf max-frame-size {
          type uint32;
          default "2000";
          description
            "Set the maximum frame size on UNI port.";
        }
        leaf poe {
          type boolean;
          default "false";
          description
            "Enable Power over Ethernet (PoE) on the UNI port.";
          reference
            "ITU-T G.988 clause 9.5.1 Physical path termination point Ethernet UNI, Power control";
        }
        leaf speed {
          type spt:speed-mode;
          default "auto";
          description
            "Sets the speed of the Ethernet port.";
        }
      }
    }
    container PON_ONU {
      description
        "PON_ONU table in ConfigDB.";
      list PON_ONU_LIST {
        key "onu-name";
        description
          "List of ONUs.
           ConfigDB key: PON_ONU|<onu-name>.";
        leaf onu-name {
          description
            "Name identifier to reference this ONU device.";
          type string {
            length "0..256";
          }
        }
        leaf device-id {
          mandatory true;
          description
            "ONU device identifier (XGS-PON: Vendor + SSN, or 'Default')";
          type string {
            pattern "([a-zA-Z]{4}[0-9a-fA-F]{8})|(Default)";
          }
        }
        leaf template-ref {
          type string;
          description
            "Reference to the ONU template to use for this ONU.";
        }
        leaf vlan-id {
          type uint16 {
            range "0..4095";
          }
          description
            "VID service configuration.";
        }
        leaf fw-bank-ptr {
          type uint16 {
            range "0..1|65535";
          }
          default "65535";
          description
            "Current Firmware bank pointer. A value of '65535' disables ONU firmware upgrade.";
        }
        leaf realtime-stats {
          type boolean;
          default "false";
          description
            "Enables the ONU state files to show all statistics on every cycle.";
        }
        leaf service-config {
          type string {
            length "0..64";
          }
          units "'Disabled' or 'Add CTag' or 'Unmodified' or <Service Config Name>";
          default "Disabled";
          description
            "ONU Service Configuration has 3 generic built-in modes and the ability to load a service configuration from the database.
             XGS supports all 3 configurations and service configuration files.
            ";
        }
        leaf service-config-omci-stats {
          type boolean;
          default "false";
          description
            "When set to true, no OMCI PM MEs will be automatically configured by the Controller.
             The PM MEs need to be specified in the ONU's SRV-CONFIG file.";
        }
        leaf fw-upgrade-backoff-delay {
          type uint32 {
            range "1..10";
          }
          units "seconds";
          default "5";
          description
            "Time to wait before retransmitting a window.";
        }
        leaf fw-upgrade-backoff-divisor {
          type uint32 {
            range "1..2";
          }
          default "2";
          description
            "Controls the size of the send window during retransmissions. A value of '2' reduces
             the send window size by half for each retransmission. A value of '1' disables the backoff.";
        }
        leaf fw-upgrade-download-format {
          type spt:fw-download-format;
          default "baseline-omci";
          description
            "The format of OMCI the PON Controller will use to upgrade the ONU, regardless of the OMCC Version it reported.";
        }
        leaf fw-upgrade-end-download-timeout {
          type uint32 {
            range "0..600";
          }
          units "seconds";
          default "0";
          description
            "Time to wait for the final acknowledgement during firmware upgrade. Increase the value
             to allow the ONU additional time to write the firmware image to flash. The PON Controller
             automatically calculates the end-download-timeout when set to a value of zero.
            ";
        }
        leaf fw-upgrade-maximum-retries {
          type uint32 {
            range "1..10";
          }
          default "4";
          description
            "Maximum number of times a window is retransmitted before terminating the ONU
             firmware upgrade and reporting an error.
            ";
        }
        leaf fw-upgrade-maximum-window-size {
          type uint32 {
            range "16..256";
          }
          units "bytes";
          default "64";
          description
            "The maximum send window sized used for transfering firmware to the ONU.";
        }
        leaf fw-upgrade-response-timeout {
          type uint32 {
            range "3..120";
          }
          units "seconds";
          default "3";
          description
            "The time in seconds to wait for an acknowledgement from the ONU during firmware upgrade.";
        }
      }
    }
    container PON_ONU_OLT_SERVICE {
      description
        "PON_ONU_OLT_SERVICE table in ConfigDB.";
      list PON_ONU_OLT_SERVICE_LIST {
        key "onu-name olt-service-id";
        description
          "OLT Configuration for the services. 0 to 7 services can be configured. A service is an XGEM Port ID/Alloc ID in XGS-PON.
           ConfigDB key: PON_ONU_OLT_SERVICE|<onu-name>|<olt-service-id>.";
        leaf onu-name {
          type leafref {
            path "/sp:sonic-pon/sp:PON_ONU/sp:PON_ONU_LIST/sp:onu-name";
          }
          description
            "References PON_ONU_LIST.";
        }
        leaf olt-service-id {
          type uint32 {
            range "0..7";
          }
          description
            "OLT Service Port number.";
        }
        leaf downstream-qos-map {
          type string {
            length "0..64";
          }
          default "";
          description
            "Reference to a Downstream QoS Map. Used with multiple XGem configurations.";
        }
        leaf enable {
          type boolean;
          default "false";
          description
            "True to enable this service port.  False to disable it.";
        }
        leaf learning-limit {
          type uint16 {
            range "0..2046";
          }
          default "2046";
          description
            "Dynamic MAC learning table size limit for this service port. A value of '0' disables MAC Learning for this service.";
        }
        leaf sla-profile {
          type string {
            length "0..64";
          }
          default "Max";
          description
            "Service level agreements for the service flow.";
        }
        leaf tcont-service-ref {
          type string {
            pattern "none|[0-7]";
          }
          description
            "none - OLT Service Port operates as a TCONT + XGem Port.
             TCONT OLT Service Port reference used to configure multiple XGem Ports for
             a single TCONT. When the value is set to a 'none', this OLT Service port operates as a
             TCONT + XGem Port. When the value references another OLT Service Port 0..7, this
             OLT Service port operates as an XGem Port only. When operating as an XGem only, this value
             must reference another OLT Service Port operating in TCONT + XGem mode.
            ";
        }
        max-elements 8;
        ordered-by system;
      }
    }
    container PON_ONU_OLT_SERVICE_NETWORK {
      description
        "PON_ONU_OLT_SERVICE_NETWORK table in ConfigDB.";
      list PON_ONU_OLT_SERVICE_NETWORK_LIST {
        key "onu-name olt-service-id vlan-id";
        description
          "List of VLAN network(s) (NNI and PON) through the service flow. VLAN Networks are defined by the SVLAN VID and two CVLAN VIDs.
           ConfigDB key: PON_ONU_OLT_SERVICE_NETWORK|<onu-name>|<olt-service-id>|<vlan-id>.";
        leaf onu-name {
          type leafref {
            path "/sp:sonic-pon/sp:PON_ONU/sp:PON_ONU_LIST/sp:onu-name";
          }
          description
            "References PON_ONU_LIST.";
        }
        leaf olt-service-id {
          type leafref {
            path "/sp:sonic-pon/sp:PON_ONU_OLT_SERVICE/sp:PON_ONU_OLT_SERVICE_LIST/sp:olt-service-id";
          }
          description
            "References PON_ONU_OLT_SERVICE_LIST.";
        }
        leaf network-id {
          type uint16 {
            range "0..999";
          }
          description
            "Index for this entry.";
        }
        leaf vlan-id {
          type uint16 {
            range "0..4095";
          }
          description
            "VID for service configuration.";
        }
        max-elements 1000;
        ordered-by system;
      }
    }
    container PON_ONU_SERVICE_CONFIG_VALUE {
      description
        "PON_ONU_SERVICE_CONFIG_VALUE table in ConfigDB.";
      list PON_ONU_SERVICE_CONFIG_VALUE_LIST {
        key "onu-name cfg-name";
        description
          "Service configuration file parameter 'onu-name' = 'value' pairs.
           ConfigDB key: PON_ONU_SERVICE_CONFIG_VALUE|<onu-name>|<cfg-name>.";
        leaf onu-name {
          type leafref {
            path "/sp:sonic-pon/sp:PON_ONU/sp:PON_ONU_LIST/sp:onu-name";
          }
          description
            "References PON_ONU_LIST.";
        }
        leaf cfg-name {
          type spt:pon-string64nz;
          description
            "Name of the service configuration parameter (e.g., 'CVID UNI').";
        }
        leaf value {
          type union {
            type uint32;
            type string {
              length "0..64";
            }
          }
          mandatory true;
          description
            "Service configuration parameter value.";
        }
        leaf value-type {
          type spt:service-config-value-type;
          must ". = 'int32' or . = 'string'";
          default "int32";
          description
            "Defines the data type for the 'value' attribute.";
        }
      }
    }
    container PON_ONU_UNI {
      description
        "PON_ONU_UNI table in ConfigDB.";
      list PON_ONU_UNI_LIST {
        key "onu-name port-id";
        description
          "Configurations for the UNI ports on the ONU.
           ConfigDB key: PON_ONU_UNI|<onu-name>|<port-id>.";
        leaf onu-name {
          type leafref {
            path "/sp:sonic-pon/sp:PON_ONU/sp:PON_ONU_LIST/sp:onu-name";
          }
          description
            "References PON_ONU_LIST.";
        }
        leaf port-id {
          type string {
            pattern 'UNI-ETH\s[1-9][0-9]?';
          }
          description
            "Identifier for this UNI port.";
        }
        leaf duplex {
          type spt:duplex-mode;
          default "auto";
          description
            "Sets the duplex for the Ethernet port.";
        }
        leaf enable {
          type boolean;
          description
            "Admin enable or disable for the UNI port.";
        }
        leaf max-frame-size {
          type uint32;
          default "2000";
          description
            "Set the maximum frame size on UNI port.";
        }
        leaf poe {
          type boolean;
          default "false";
          description
            "Enable Power over Ethernet (PoE) on the UNI port.";
          reference
            "ITU-T G.988 clause 9.5.1 Physical path termination point Ethernet UNI, Power control";
        }
        leaf speed {
          type spt:speed-mode;
          default "auto";
          description
            "Sets the speed of the Ethernet port.";
        }
      }
    }
    container PON_ONU_FW_BANK_FILE {
      description
        "PON_ONU_FW_BANK_FILE table in ConfigDB.";
      list PON_ONU_FW_BANK_FILE_LIST {
        key "onu-name bank-id";
        description
          "XGS-PON: firmware source filenames for bank 0 (1st in list) and bank 1 if version doesn't match.

           ConfigDB key: PON_ONU_FW_BANK_FILE|<onu-name>|<bank-id>.";
        leaf onu-name {
          type leafref {
            path "/sp:sonic-pon/sp:PON_ONU/sp:PON_ONU_LIST/sp:onu-name";
          }
          description
            "References PON_ONU_LIST.";
        }
        leaf bank-id {
          type uint8 {
            range "0..1";
          }
          description
            "Index for this entry.";
        }
        leaf file {
          type string {
            length "0..64";
          }
          description
            "Name of the firmware file.";
        }
        leaf version {
          type string {
            length "0..64";
          }
          description
            "Version.";
        }
        max-elements 2;
        ordered-by system;
      }
    }
    container PON_SERVICE_CONFIG_PROFILE_HEADER {
      description
        "Service configuration header. ConfigDB table: PON_SERVICE_CONFIG_PROFILE_HEADER.";
      list PON_SERVICE_CONFIG_PROFILE_HEADER_LIST {
        key "name";
        description
          "PON_SERVICE_CONFIG_PROFILE_HEADER configuration.
           ConfigDB key: PON_SERVICE_CONFIG_PROFILE_HEADER|<name>.";
        leaf name {
          type string;
          description
            "ONU vendor name.";
        }
        leaf title {
          type string;
          description
            "Description for this service configuration.";
        }
        leaf version {
          type string;
          description
            "Capability of configuration file format.";
        }
      }
    }
    container PON_SERVICE_CONFIG_PROFILE_HEADER_COMPATIBILITY_VENDOR_MODEL {
      description
        "PON_SERVICE_CONFIG_PROFILE_HEADER_COMPATIBILITY_VENDOR_MODEL table in ConfigDB.";
      list PON_SERVICE_CONFIG_PROFILE_HEADER_COMPATIBILITY_VENDOR_MODEL_LIST {
        key "vendor-id name";
        description
          "PON_SERVICE_CONFIG_PROFILE_HEADER_COMPATIBILITY_VENDOR_MODEL configuration.
           ConfigDB key: PON_SERVICE_CONFIG_PROFILE_HEADER_COMPATIBILITY_VENDOR_MODEL|<vendor-id>|<name>.";
        leaf vendor-id {
          type string;
        }
        leaf name {
          type leafref {
            path "/sp:sonic-pon/sp:PON_SERVICE_CONFIG_PROFILE_HEADER/sp:PON_SERVICE_CONFIG_PROFILE_HEADER_LIST/sp:name";
          }
          description
            "References PON_SERVICE_CONFIG_PROFILE_HEADER_LIST.";
        }
        leaf-list model {
          type string;
          description
            "ONU model number.";
        }
      }
    }
    container PON_SERVICE_CONFIG_PROFILE_HEADER_INPUTS_EXT_INPUT {
      description
        "PON_SERVICE_CONFIG_PROFILE_HEADER_INPUTS_EXT_INPUT table in ConfigDB.";
      list PON_SERVICE_CONFIG_PROFILE_HEADER_INPUTS_EXT_INPUT_LIST {
        key "name db-ref";
        description
          "PON_SERVICE_CONFIG_PROFILE_HEADER_INPUTS_EXT_INPUT configuration.
           ConfigDB key: PON_SERVICE_CONFIG_PROFILE_HEADER_INPUTS_EXT_INPUT|<name>|<db-ref>.";
        leaf name {
          type leafref {
            path "/sp:sonic-pon/sp:PON_SERVICE_CONFIG_PROFILE_HEADER/sp:PON_SERVICE_CONFIG_PROFILE_HEADER_LIST/sp:name";
          }
          description
            "References PON_SERVICE_CONFIG_PROFILE_HEADER_LIST.";
        }
        leaf db-ref {
          type omci-types:omci-db-ref;
          description
            "Path referencing a specific collection and field in the database.";
        }
        leaf type {
          type omci-types:header-input-type;
          description
            "Input data type.";
        }
      }
    }
    container PON_SERVICE_CONFIG_PROFILE_ANI_G {
      description
        "ANI-G, Class Value 263. This ME organizes data associated with each access network interface supported by a G-PON ONU. The ONU automatically creates one instance of this ME for each PON physical port. ConfigDB table: PON_SERVICE_CONFIG_PROFILE_ANI_G.";
      reference
        "G.988, 9.2.1, ANI-G";
      list PON_SERVICE_CONFIG_PROFILE_ANI_G_LIST {
        key "service-config-profile-name managed-entity-id";
        description
          "PON_SERVICE_CONFIG_PROFILE_OMCI_CLASS_ANI_G_MANAGED_ENTITY configuration.
           ConfigDB key: PON_SERVICE_CONFIG_PROFILE_ANI_G|<service-config-profile-name>|<managed-entity-id>.";
        leaf service-config-profile-name {
          type string;
          description
            "Service configuration profile identifier that scopes ANI-G managed entities.";
        }
        leaf managed-entity-id {
          type omci-types:omci-uint16;
          description
            "Managed entity ID for ANI-G. The value indicates the physical position of the PON interface.";
        }
        leaf gem-block-length {
          type omci-types:omci-uint16;
          description
            "Queue occupancy reporting granularity for DBA, expressed in bytes.";
        }
        leaf sf-threshold {
          type omci-types:omci-uint8;
          description
            "Signal fail BER threshold exponent y, where threshold is 10^(-y).";
        }
        leaf sd-threshold {
          type omci-types:omci-uint8;
          description
            "Signal degrade BER threshold exponent x, where threshold is 10^(-x).";
        }
        leaf arc {
          type omci-types:omci-uint8;
          description
            "Alarm-reporting control (ARC) value.";
        }
        leaf arc-interval {
          type omci-types:omci-uint8;
          description
            "Alarm-reporting control interval.";
        }
        leaf lower-optical-threshold {
          type omci-types:omci-uint8;
          description
            "Lower received optical power threshold used for low-power alarm detection.";
        }
        leaf upper-optical-threshold {
          type omci-types:omci-uint8;
          description
            "Upper received optical power threshold used for high-power alarm detection.";
        }
        leaf lower-transmit-power-threshold {
          type omci-types:omci-uint8;
          description
            "Lower transmit optical launch power threshold for low transmit power alarm.";
        }
        leaf upper-transmit-power-threshold {
          type omci-types:omci-uint8;
          description
            "Upper transmit optical launch power threshold for high transmit power alarm.";
        }
      }
    }
    container PON_SERVICE_CONFIG_PROFILE_CARDHOLDER {
      description
        "Cardholder, Class Value 5. This ME represents ONU slot/cardholder provisioning and expected equipment attributes for circuit pack realization. ConfigDB table: PON_SERVICE_CONFIG_PROFILE_CARDHOLDER.";
      reference
        "G.988, 9.1.5, Cardholder";
      list PON_SERVICE_CONFIG_PROFILE_CARDHOLDER_LIST {
        key "service-config-profile-name managed-entity-id";
        description
          "PON_SERVICE_CONFIG_PROFILE_OMCI_CLASS_CARDHOLDER_MANAGED_ENTITY configuration.
           ConfigDB key: PON_SERVICE_CONFIG_PROFILE_CARDHOLDER|<service-config-profile-name>|<managed-entity-id>.";
        leaf service-config-profile-name {
          type string;
          description
            "Service configuration profile identifier that scopes Cardholder managed entities.";
        }
        leaf managed-entity-id {
          type omci-types:omci-uint16;
          description
            "Managed entity ID that uniquely identifies the Cardholder instance.";
        }
        leaf expected-plugin-unit-type {
          type omci-types:omci-uint8;
          description
            "Provisioned expected circuit pack type for the slot.";
        }
        leaf expected-port-count {
          type omci-types:omci-uint8;
          description
            "Expected number of ports in the circuit pack.";
        }
        leaf expected-equipment-id {
          type omci-types:omci-string;
          description
            "Expected specific equipment identifier for the circuit pack.";
        }
        leaf invoke-protection-switch {
          type omci-types:omci-uint8;
          description
            "Protection switching control value used by OLT to control protection state.";
        }
        leaf arc {
          type omci-types:omci-uint8;
          description
            "Alarm-reporting control (ARC) value.";
        }
        leaf arc-interval {
          type omci-types:omci-uint8;
          description
            "Alarm-reporting control interval.";
        }
      }
    }
    container PON_SERVICE_CONFIG_PROFILE_CIRCUIT_PACK {
      description
        "Circuit pack, Class Value 6. This ME models a real or virtual circuit pack that is equipped in a real or virtual ONU slot. For ONUs with integrated interfaces, this ME may be used to distinguish available types of interfaces (the port-mapping package is another way). For ONUs with integrated interfaces, the ONU automatically creates an instance of this ME for each instance of the virtual cardholder ME. The ONU also creates an instance of this ME when the OLT provisions the cardholder to expect a circuit pack, i.e., when the OLT sets the expected plug-in unit type or equipment ID of the cardholder to a circuit pack type, as defined in Table 9.1.5-1. The ONU also creates an instance of this ME when a circuit pack is installed in a cardholder whose expected plug-in unit type is 255= plug-and- play, and whose equipment ID is not provisioned. Finally, when the cardholder is provisioned for plug-and-play, an instance of this ME can be created at the request of the OLT. The ONU deletes an instance of this ME when the OLT de-provisions the circuit pack (i.e., when the OLT sets the expected plug-in unit type or equipment ID of the cardholder to 0= no LIM). The ONU also deletes an instance of this ME on request of the OLT if the expected plug-in unit type attribute of the corresponding cardholder is equal to 255, plug-and-play, and the expected equipment ID is blank (a string of all spaces). ONUs with integrated interfaces do not delete circuit pack instances. NOTE Creation and deletion by the OLT is retained for backward compatibility. ConfigDB table: PON_SERVICE_CONFIG_PROFILE_CIRCUIT_PACK.";
      reference
        "G.988, 9.1.6, Circuit pack";
      list PON_SERVICE_CONFIG_PROFILE_CIRCUIT_PACK_LIST {
        key "service-config-profile-name managed-entity-id";
        description
          "PON_SERVICE_CONFIG_PROFILE_OMCI_CLASS_CIRCUIT_PACK_MANAGED_ENTITY configuration.
           ConfigDB key: PON_SERVICE_CONFIG_PROFILE_CIRCUIT_PACK|<service-config-profile-name>|<managed-entity-id>.";
        leaf service-config-profile-name {
          type string;
          description
            "Service configuration profile identifier that scopes Circuit pack managed entities.";
        }
        leaf managed-entity-id {
          type omci-types:omci-uint16;
          description
            "Managed entity ID that uniquely identifies the Circuit pack instance.";
        }
        leaf administrative-state {
          type omci-types:omci-uint8;
          description
            "Administrative state of this circuit pack instance (for example lock or unlock).";
        }
        leaf bridged-or-ip-ind {
          type omci-types:omci-uint8;
          description
            "Indicates whether an Ethernet interface is bridged, IP router based, or both.";
        }
        leaf card-configuration {
          type omci-types:omci-uint8;
          description
            "Configuration selector for configurable circuit pack variants.";
        }
        leaf power-sched-override {
          type omci-types:omci-uint32;
          description
            "Power sched override mask controlling ports excluded from power shedding.";
        }
      }
    }
    container PON_SERVICE_CONFIG_PROFILE_ENHANCED_FEC_PM_HIST_DATA {
      description
        "Enhanced FEC performance monitoring history data, Class Value 453. This ME collects PM data associated with PON downstream FEC counters for XGS-PON and subsequent ITU-T PON systems. Instances of this ME are created and deleted by the OLT. For a complete discussion of generic PM architecture, refer to clause I.4. ConfigDB table: PON_SERVICE_CONFIG_PROFILE_ENHANCED_FEC_PM_HIST_DATA.";
      reference
        "G.988, 9.2.22, Enhanced FEC performance monitoring history data";
      list PON_SERVICE_CONFIG_PROFILE_ENHANCED_FEC_PM_HIST_DATA_LIST {
        key "service-config-profile-name managed-entity-id";
        description
          "PON_SERVICE_CONFIG_PROFILE_OMCI_CLASS_ENHANCED_FEC_PM_HIST_DATA_MANAGED_ENTITY  configuration.
           ConfigDB key: PON_SERVICE_CONFIG_PROFILE_ENHANCED_FEC_PM_HIST_DATA|<service-config-profile-name>|<managed-entity-id>.";
        leaf service-config-profile-name {
          type string;
          description
            "Service configuration profile identifier that scopes Enhanced FEC PM entities.";
        }
        leaf managed-entity-id {
          type omci-types:omci-uint16;
          description
            "Managed entity ID linked to ANI-G or TWDM channel context.";
        }
        leaf threshold-data-64-bit-id {
          type omci-types:omci-uint16;
          description
            "Reference to threshold data 64-bit managed entity containing PM thresholds.";
        }
      }
    }
    container PON_SERVICE_CONFIG_PROFILE_ENHANCED_TC_PERF_MON_HIST_DATA {
      description
        "Enhanced TC performance monitoring history data, Class Value 454. This ME collects PM data associated with the XGS-PON and subsequent ITU-T PON systems' TC layer. For a complete discussion of generic PM architecture, refer to clause I.4. ConfigDB table: PON_SERVICE_CONFIG_PROFILE_ENHANCED_TC_PERF_MON_HIST_DATA.";
      reference
        "G.988, 9.2.23, Enhanced TC performance monitoring history data";
      list PON_SERVICE_CONFIG_PROFILE_ENHANCED_TC_PERF_MON_HIST_DATA_LIST {
        key "service-config-profile-name managed-entity-id";
        description
          "PON_SERVICE_CONFIG_PROFILE_OMCI_CLASS_ENHANCED_TC_PERF_MON_HIST_DATA_MANAGED_ENTITY configuration.
           ConfigDB key: PON_SERVICE_CONFIG_PROFILE_ENHANCED_TC_PERF_MON_HIST_DATA|<service-config-profile-name>|<managed-entity-id>.";
        leaf service-config-profile-name {
          type string;
          description
            "Service configuration profile identifier that scopes Enhanced TC PM entities.";
        }
        leaf managed-entity-id {
          type omci-types:omci-uint16;
          description
            "Managed entity ID linked to ANI-G context for this PM instance.";
        }
        leaf threshold-data-64-bit-id {
          type omci-types:omci-uint16;
          description
            "Reference to threshold data 64-bit managed entity containing PM thresholds.";
        }
      }
    }
    container PON_SERVICE_CONFIG_PROFILE_ETHERNET_FRAME_EXTENDED_PM {
      description
        "Ethernet frame extended PM, Class Value 334. This ME collects some of the PM data at a point where an Ethernet flow can be observed. It is based on the Etherstats group of [IETF RFC 2819]. Instances of this ME are created and deleted by the OLT. References to received frames are to be interpreted as the number of frames entering the monitoring point in the direction specified by the control block. For a complete discussion of generic PM architecture, refer to clause I.4. ConfigDB table: PON_SERVICE_CONFIG_PROFILE_ETHERNET_FRAME_EXTENDED_PM.";
      reference
        "G.988, 9.3.32, Ethernet frame extended PM";
      list PON_SERVICE_CONFIG_PROFILE_ETHERNET_FRAME_EXTENDED_PM_LIST {
        key "service-config-profile-name managed-entity-id";
        description
          "PON_SERVICE_CONFIG_PROFILE_OMCI_CLASS_ETHERNET_FRAME_EXTENDED_PM_MANAGED_ENTITY configuration.
           ConfigDB key: PON_SERVICE_CONFIG_PROFILE_ETHERNET_FRAME_EXTENDED_PM|<service-config-profile-name>|<managed-entity-id>.";
        leaf service-config-profile-name {
          type string;
        }
        leaf managed-entity-id {
          type omci-types:omci-uint16;
          description
            "Managed entity ID: This attribute uniquely identifies each instance of this ME. To facilitate discovery, the identification of instances sequentially starting with 1 is encouraged. (R, set-by-create) (mandatory) (2 bytes)";
        }
        leaf threshold-data-id {
          type omci-types:omci-uint16;
          description
            "threshold data id";
        }
        leaf parent-me-class {
          type omci-types:omci-uint16;
          description
            "parent me class";
        }
        leaf parent-me-instance {
          type omci-types:omci-uint16;
          description
            "parent me instance";
        }
        leaf accumulation-disable {
          type omci-types:omci-uint16;
          description
            "accumulation disable";
        }
        leaf tca-disable {
          type omci-types:omci-uint16;
          description
            "tca disable";
        }
        leaf control-fields {
          type omci-types:omci-uint16;
          description
            "control fields";
        }
        leaf tci {
          type omci-types:omci-uint16;
          description
            "tci";
        }
        leaf reserved {
          type omci-types:omci-uint16;
          description
            "reserved";
        }
      }
    }
    container PON_SERVICE_CONFIG_PROFILE_ETHERNET_FRAME_EXTENDED_PM64_BIT {
      description
        "Ethernet frame extended PM 64-bit, Class Value 425. This ME collects some of the PM data at a point where an Ethernet flow can be observed. It is based on the Etherstats group of [IETF RFC 2819] and [IETF RFC 2863]. Instances of this ME are created and deleted by the OLT. References to received frames are to be interpreted as the number of frames entering the monitoring point in the direction specified by the control block. For a complete discussion of generic PM architecture, refer to clause I.4. ConfigDB table: PON_SERVICE_CONFIG_PROFILE_ETHERNET_FRAME_EXTENDED_PM64_BIT.";
      reference
        "G.988, 9.3.34, Ethernet frame extended PM 64-bit";
      list PON_SERVICE_CONFIG_PROFILE_ETHERNET_FRAME_EXTENDED_PM64_BIT_LIST {
        key "service-config-profile-name managed-entity-id";
        description
          "PON_SERVICE_CONFIG_PROFILE_OMCI_CLASS_ETHERNET_FRAME_EXTENDED_PM64_BIT_MANAGED_ENTITY configuration.
           ConfigDB key: PON_SERVICE_CONFIG_PROFILE_ETHERNET_FRAME_EXTENDED_PM64_BIT|<service-config-profile-name>|<managed-entity-id>.";
        leaf service-config-profile-name {
          type string;
        }
        leaf managed-entity-id {
          type omci-types:omci-uint16;
          description
            "Managed entity ID: This attribute uniquely identifies each instance of this ME. To facilitate discovery, it is encouraged to identify instances sequentially starting with 1. (R, set-by-create) (mandatory) (2 bytes)";
        }
        leaf threshold-data-id {
          type omci-types:omci-uint16;
          description
            "threshold data id";
        }
        leaf parent-me-class {
          type omci-types:omci-uint16;
          description
            "parent me class";
        }
        leaf parent-me-instance {
          type omci-types:omci-uint16;
          description
            "parent me instance";
        }
        leaf accumulation-disable {
          type omci-types:omci-uint16;
          description
            "accumulation disable";
        }
        leaf tca-disable {
          type omci-types:omci-uint16;
          description
            "tca disable";
        }
        leaf control-fields {
          type omci-types:omci-uint16;
          description
            "control fields";
        }
        leaf tci {
          type omci-types:omci-uint16;
          description
            "tci";
        }
        leaf reserved {
          type omci-types:omci-uint16;
          description
            "reserved";
        }
      }
    }
    container PON_SERVICE_CONFIG_PROFILE_ETHERNET_FRAME_PERF_MON_HIST_DATA_DOWNSTREAM {
      description
        "Ethernet frame performance monitoring history data downstream, Class Value 321. This ME is identical to the Ethernet frame PM history data upstream ME, with the exception that it monitors downstream traffic. ConfigDB table: PON_SERVICE_CONFIG_PROFILE_ETHERNET_FRAME_PERF_MON_HIST_DATA_DOWNSTREAM.";
      reference
        "G.988, 9.3.31, Ethernet frame performance monitoring history data downstream";
      list PON_SERVICE_CONFIG_PROFILE_ETHERNET_FRAME_PERF_MON_HIST_DATA_DOWNSTREAM_LIST {
        key "service-config-profile-name managed-entity-id";
        description
          "PON_SERVICE_CONFIG_PROFILE_OMCI_CLASS_ETHERNET_FRAME_PERF_MON_HIST_DATA_DOWNSTREAM_MANAGED_ENTITY configuration.
           ConfigDB key: PON_SERVICE_CONFIG_PROFILE_ETHERNET_FRAME_PERF_MON_HIST_DATA_DOWNSTREAM|<service-config-profile-name>|<managed-entity-id>.";
        leaf service-config-profile-name {
          type string;
        }
        leaf managed-entity-id {
          type omci-types:omci-uint16;
          description
            "Managed entity ID: This attribute uniquely identifies each instance of this ME. Through an identical ID, this ME is implicitly linked to an instance of a MAC bridge port configuration data. (R, set-by-create) (mandatory) (2bytes)";
        }
        leaf threshold-data-1-2-id {
          type omci-types:omci-uint16;
          description
            "Threshold data 1/2 ID: This attribute points to an instance of the threshold data 1 ME that contains PM threshold values. Since no threshold value attribute number exceeds 7, a threshold data 2 ME is optional. (R,W, set-by-create) (mandatory) (2bytes)";
        }
      }
    }
    container PON_SERVICE_CONFIG_PROFILE_ETHERNET_FRAME_PERF_MON_HIST_DATA_UPSTREAM {
      description
        "Ethernet frame performance monitoring history data upstream, Class Value 322. This ME collects PM data associated with upstream Ethernet frame delivery. It is based on the Etherstats group of [IETF RFC 2819]. Instances of this ME are created and deleted by the OLT. For a complete discussion of generic PM architecture, refer to clause I.4. NOTE1Implementers are encouraged to consider the Ethernet frame extended PM ME defined in clause9.3.32, which collects the same counters in a more generalized way. ConfigDB table: PON_SERVICE_CONFIG_PROFILE_ETHERNET_FRAME_PERF_MON_HIST_DATA_UPSTREAM.";
      reference
        "G.988, 9.3.30, Ethernet frame performance monitoring history data upstream";
      list PON_SERVICE_CONFIG_PROFILE_ETHERNET_FRAME_PERF_MON_HIST_DATA_UPSTREAM_LIST {
        key "service-config-profile-name managed-entity-id";
        description
          "PON_SERVICE_CONFIG_PROFILE_OMCI_CLASS_ETHERNET_FRAME_PERF_MON_HIST_DATA_UPSTREAM_MANAGED_ENTITY configuration.
           ConfigDB key: PON_SERVICE_CONFIG_PROFILE_ETHERNET_FRAME_PERF_MON_HIST_DATA_UPSTREAM|<service-config-profile-name>|<managed-entity-id>.";
        leaf service-config-profile-name {
          type string;
        }
        leaf managed-entity-id {
          type omci-types:omci-uint16;
          description
            "Managed entity ID: This attribute uniquely identifies each instance of this ME. Through an identical ID, this ME is implicitly linked to an instance of a MAC bridge port configuration data. (R, set-by-create) (mandatory) (2bytes)";
        }
        leaf threshold-data-1-2-id {
          type omci-types:omci-uint16;
          description
            "Threshold data 1/2 ID: This attribute points to an instance of the threshold data 1 ME that contains PM threshold values. Since no threshold value attribute number exceeds 7, a threshold data 2 ME is optional. (R,W, set-by-create) (mandatory) (2bytes)";
        }
      }
    }
    container PON_SERVICE_CONFIG_PROFILE_ETHERNET_PERF_MON_HIST_DATA {
      description
        "Ethernet performance monitoring history data, Class Value 24. This ME collects some of the PM data for a physical Ethernet interface. Instances of this ME are created and deleted by the OLT. For a complete discussion of generic PM architecture, refer to clause I.4. ConfigDB table: PON_SERVICE_CONFIG_PROFILE_ETHERNET_PERF_MON_HIST_DATA.";
      reference
        "G.988, 9.5.2, Ethernet performance monitoring history data";
      list PON_SERVICE_CONFIG_PROFILE_ETHERNET_PERF_MON_HIST_DATA_LIST {
        key "service-config-profile-name managed-entity-id";
        description
          "PON_SERVICE_CONFIG_PROFILE_OMCI_CLASS_ETHERNET_PERF_MON_HIST_DATA_MANAGED_ENTITY configuration.
           ConfigDB key: PON_SERVICE_CONFIG_PROFILE_ETHERNET_PERF_MON_HIST_DATA|<service-config-profile-name>|<managed-entity-id>.";
        leaf service-config-profile-name {
          type string;
        }
        leaf managed-entity-id {
          type omci-types:omci-uint16;
          description
            "Managed entity ID: This attribute uniquely identifies each instance of this ME. Through an identical ID, this ME is implicitly linked to an instance of the PPTP Ethernet UNI. (R, set-by-create) (mandatory) (2bytes)";
        }
        leaf threshold-data-1-2-id {
          type omci-types:omci-uint16;
          description
            "Threshold data 1/2 ID: This attribute points to an instance of the threshold data 1 and 2 MEs that contains PM threshold values. (R,W, set-by-create) (mandatory) (2bytes)";
        }
      }
    }
    container PON_SERVICE_CONFIG_PROFILE_ETHERNET_PERF_MON_HIST_DATA3 {
      description
        "Ethernet performance monitoring history data 3, Class Value 296. This ME collects PM data associated with an Ethernet interface. It includes parameters defined in the Ethernet statistics group of [IETF RFC 2819] that are not already covered by previously defined Ethernet monitoring MEs. The received direction is from the CPE towards the network (upstream). NOTE 1 Several of the same counters are available from the Ethernet frame PM history data MEs, which are associated with MAC bridge ports. MAC bridge port association allows those MEs to be used for any Ethernet flow, in both upstream and downstream directions, while the Ethernet PM history data 3 ME can only be used on a physical IEEE 802.3 port. Instances of this ME are created and deleted by the OLT. For a complete discussion of generic PM architecture, refer to clause I.4. NOTE 2 Implementers are encouraged to consider the Ethernet frame extended PM ME defined in clause9.3.32, which collects the same counters in a more generalized way. ConfigDB table: PON_SERVICE_CONFIG_PROFILE_ETHERNET_PERF_MON_HIST_DATA3.";
      reference
        "G.988, 9.5.4, Ethernet performance monitoring history data 3";
      list PON_SERVICE_CONFIG_PROFILE_ETHERNET_PERF_MON_HIST_DATA3_LIST {
        key "service-config-profile-name managed-entity-id";
        description
          "PON_SERVICE_CONFIG_PROFILE_OMCI_CLASS_ETHERNET_PERF_MON_HIST_DATA3_MANAGED_ENTITY configuration.
           ConfigDB key: PON_SERVICE_CONFIG_PROFILE_ETHERNET_PERF_MON_HIST_DATA3|<service-config-profile-name>|<managed-entity-id>.";
        leaf service-config-profile-name {
          type string;
        }
        leaf managed-entity-id {
          type omci-types:omci-uint16;
          description
            "Managed entity ID: This attribute uniquely identifies each instance of this ME. Through an identical ID, this ME is implicitly linked to an instance of the PPTP Ethernet UNI. (R, set-by-create) (mandatory) (2bytes)";
        }
        leaf threshold-data-1-2-id {
          type omci-types:omci-uint16;
          description
            "Threshold data 1/2 ID: This attribute points to an instance of the threshold data 1 ME that contains PM threshold values. Since no threshold value attribute number exceeds 7, a threshold data 2 ME is optional. (R,W, set-by-create) (mandatory) (2bytes)";
        }
      }
    }
    container PON_SERVICE_CONFIG_PROFILE_EXTENDED_VLAN_TAGGING_OPERATION_CONFIG_DATA {
      description
        "Extended VLAN tagging operation configuration data, Class Value 171. This ME organizes data associated with VLAN classification and tagging operations. Regardless of its point of attachment, the specified tagging operations refer to the upstream direction. Instances of this ME are created and deleted by the OLT. Through separate attributes, this ME supports either a Received frame VLAN tagging operation table attribute in its backward compatible form, or an enhanced frame classification and processing capability. The OLT can determine whether the ONU supports the enhanced capability through the Enhanced mode attribute of the ONU3-G ME. ConfigDB table: PON_SERVICE_CONFIG_PROFILE_EXTENDED_VLAN_TAGGING_OPERATION_CONFIG_DATA.";
      reference
        "G.988, 9.3.13, Extended VLAN tagging operation configuration data";
      list PON_SERVICE_CONFIG_PROFILE_EXTENDED_VLAN_TAGGING_OPERATION_CONFIG_DATA_LIST {
        key "service-config-profile-name managed-entity-id";
        description
          "PON_SERVICE_CONFIG_PROFILE_OMCI_CLASS_EXTENDED_VLAN_TAGGING_OPERATION_CONFIG_DATA_MANAGED_ENTITY configuration.
           ConfigDB key: PON_SERVICE_CONFIG_PROFILE_EXTENDED_VLAN_TAGGING_OPERATION_CONFIG_DATA|<service-config-profile-name>|<managed-entity-id>.";
        leaf service-config-profile-name {
          type string;
        }
        leaf managed-entity-id {
          type omci-types:omci-uint16;
          description
            "Managed entity ID: This attribute provides a unique number for each instance of this ME. (R, set-by-create) (mandatory) (2bytes)";
        }
        leaf association-type {
          type omci-types:omci-uint8;
          description
            "Association type: This attribute identifies the type of the ME associated with this extended VLAN tagging ME. Values are assigned as follows. 0 MAC bridge port configuration data 1 IEEE 802.1p mapper service profile 2 Physical path termination point Ethernet UNI 3 IP host config data or IPv6 host config data 4 Physical path termination point xDSL UNI 5 GEM IW termination point 6 Multicast GEM IW termination point 7 Physical path termination point MoCA UNI 8 Reserved 9 Ethernet flow termination point 10 Virtual Ethernet interface point 11 MPLS pseudowire termination point 12 EFM bonding group (R,W, set-by-create) (mandatory) (1byte) NOTE 1 If a MAC bridge is configured, code points 1, 5, 6 and 11 are associated with the ANI side of the MAC bridge. Code point 0 is associated with the ANI or UNI side, depending on the location of the MAC bridge port. The other code points are associated with the UNI side. When the extended VLAN tagging ME is associated with the ANI side, it behaves as an upstream egress rule, and as a downstream ingress rule when the downstream mode attribute is equal to 0. When the extended VLAN tagging ME is associated with the UNI side, the extended VLAN tagging ME behaves as an upstream ingress rule, and as a downstream egress rule when the downstream mode attribute is equal to 0.";
        }
        leaf input-tpid {
          type omci-types:omci-uint16;
          description
            "Input TPID: This attribute gives the special TPID value for operations on the input (filtering) side of the table. Typical values include 0x88A8 and 0x9100. (R,W) (mandatory) (2bytes)";
        }
        leaf output-tpid {
          type omci-types:omci-uint16;
          description
            "Output TPID: This attribute gives the special TPID value for operations on the output (tagging) side of the table. Typical values include 0x88A8 and 0x9100. (R,W) (mandatory) (2bytes)";
        }
        leaf downstream-mode {
          type omci-types:omci-uint8;
        }
        leaf associated-me-pointer {
          type omci-types:omci-uint16;
          description
            "Associated ME pointer: This attribute points to the ME with which this extended VLAN tagging operation configuration data ME is associated. (R,W, set-by- create) (mandatory) (2bytes) NOTE 5 When the association type is xDSL, the two MSBs may be used to indicate a bearer channel.";
        }
      }
    }
    container PON_SERVICE_CONFIG_PROFILE_EXTENDED_VLAN_TAGGING_OPERATION_CONFIG_DATA_RECEIVED_FRAME_VLAN_TAGGING_OPERATION {
      description
        "Received frame VLAN tagging operation table entry for Extended VLAN tagging operation configuration data. Each entry defines a frame filter and VLAN treatment rule. ConfigDB table: PON_SERVICE_CONFIG_PROFILE_EXTENDED_VLAN_TAGGING_OPERATION_CONFIG_DATA_RECEIVED_FRAME_VLAN_TAGGING_OPERATION.";
      list PON_SERVICE_CONFIG_PROFILE_EXTENDED_VLAN_TAGGING_OPERATION_CONFIG_DATA_RECEIVED_FRAME_VLAN_TAGGING_OPERATION_LIST {
        key "service-config-profile-name id managed-entity-id received-frame-vlan-tagging-operation-table-entry-id";
        description
          "PON_SERVICE_CONFIG_PROFILE_OMCI_CLASS_EXTENDED_VLAN_TAGGING_OPERATION_CONFIG_DATA_MANAGED_ENTITY_RECEIVED_FRAME_VLAN_TAGGING_OPERATION configuration.
           ConfigDB key: PON_SERVICE_CONFIG_PROFILE_EXTENDED_VLAN_TAGGING_OPERATION_CONFIG_DATA_RECEIVED_FRAME_VLAN_TAGGING_OPERATION|<service-config-profile-name>|<id>|<managed-entity-id>|<received-frame-vlan-tagging-operation-table-entry-id>.";
        leaf service-config-profile-name {
          type string;
        }
        leaf id {
          type string;
          description
            "Table entry number starting at '0'";
        }
        leaf managed-entity-id {
          type omci-types:omci-uint16;
          description
            "Managed entity ID: This attribute provides a unique number for each instance of this ME. (R, set-by-create) (mandatory) (2bytes)";
        }
        leaf received-frame-vlan-tagging-operation-table-entry-id {
          type uint8;
        }
        leaf filter-outer-priority {
          type omci-types:omci-uint16;
          description
            "filter outer priority";
        }
        leaf filter-outer-vid {
          type omci-types:omci-uint16;
          description
            "filter outer vid";
        }
        leaf filter-outer-tpid-de {
          type omci-types:omci-uint16;
          description
            "filter outer tpid de";
        }
        leaf pad1 {
          type omci-types:omci-uint16;
          description
            "pad1";
        }
        leaf filter-inner-priority {
          type omci-types:omci-uint16;
          description
            "filter inner priority";
        }
        leaf filter-inner-vid {
          type omci-types:omci-uint16;
          description
            "filter inner vid";
        }
        leaf filter-inner-tpid-de {
          type omci-types:omci-uint16;
          description
            "filter inner tpid de";
        }
        leaf pad2 {
          type omci-types:omci-uint16;
          description
            "pad2";
        }
        leaf filter-ether-type {
          type omci-types:omci-uint16;
          description
            "filter ether type";
        }
        leaf treatment-tags-to-remove {
          type omci-types:omci-uint16;
          description
            "treatment tags to remove";
        }
        leaf pad3 {
          type omci-types:omci-uint16;
          description
            "pad3";
        }
        leaf treatment-outer-priority {
          type omci-types:omci-uint16;
          description
            "treatment outer priority";
        }
        leaf treatment-outer-vid {
          type omci-types:omci-uint16;
          description
            "treatment outer vid";
        }
        leaf treatment-outer-tpid-de {
          type omci-types:omci-uint16;
          description
            "treatment outer tpid de";
        }
        leaf pad4 {
          type omci-types:omci-uint16;
          description
            "pad4";
        }
        leaf treatment-inner-priority {
          type omci-types:omci-uint16;
          description
            "treatment inner priority";
        }
        leaf treatment-inner-vid {
          type omci-types:omci-uint16;
          description
            "treatment inner vid";
        }
        leaf treatment-inner-tpid-de {
          type omci-types:omci-uint16;
          description
            "treatment inner tpid de";
        }
      }
    }
    container PON_SERVICE_CONFIG_PROFILE_EXTENDED_VLAN_TAGGING_OPERATION_CONFIG_DATA_DSCP_TO_PBIT_MAPPING {
      description
        "DSCP to P-bit mapping entry for Extended VLAN tagging operation configuration data. ConfigDB table: PON_SERVICE_CONFIG_PROFILE_EXTENDED_VLAN_TAGGING_OPERATION_CONFIG_DATA_DSCP_TO_PBIT_MAPPING.";
      list PON_SERVICE_CONFIG_PROFILE_EXTENDED_VLAN_TAGGING_OPERATION_CONFIG_DATA_DSCP_TO_PBIT_MAPPING_LIST {
        key "service-config-profile-name id managed-entity-id dscp";
        description
          "PON_SERVICE_CONFIG_PROFILE_OMCI_CLASS_EXTENDED_VLAN_TAGGING_OPERATION_CONFIG_DATA_MANAGED_ENTITY_DSCP_TO_PBIT_MAPPING configuration.
           ConfigDB key: PON_SERVICE_CONFIG_PROFILE_EXTENDED_VLAN_TAGGING_OPERATION_CONFIG_DATA_DSCP_TO_PBIT_MAPPING|<service-config-profile-name>|<id>|<managed-entity-id>|<dscp>.";
        leaf service-config-profile-name {
          type string;
        }
        leaf id {
          type string;
          description
            "Table entry number starting at '0'";
        }
        leaf managed-entity-id {
          type omci-types:omci-uint16;
          description
            "Managed entity ID: This attribute provides a unique number for each instance of this ME. (R, set-by-create) (mandatory) (2bytes)";
        }
        leaf dscp {
          type uint8;
          description
            "DSCP Value";
        }
        leaf priority {
          type uint8;
          description
            "P-bit value";
        }
      }
    }
    container PON_SERVICE_CONFIG_PROFILE_FEC_PERF_MON_HIST_DATA {
      description
        "FEC performance monitoring history data, Class Value 312. This ME collects PM data associated with PON downstream forward error correction (FEC) counters. Instances of this ME are created and deleted by the OLT. For a complete discussion of generic PM architecture, refer to clause I.4. ConfigDB table: PON_SERVICE_CONFIG_PROFILE_FEC_PERF_MON_HIST_DATA.";
      reference
        "G.988, 9.2.9, Forward error correction performance monitoring history data";
      list PON_SERVICE_CONFIG_PROFILE_FEC_PERF_MON_HIST_DATA_LIST {
        key "service-config-profile-name managed-entity-id";
        description
          "PON_SERVICE_CONFIG_PROFILE_OMCI_CLASS_FEC_PERF_MON_HIST_DATA_MANAGED_ENTITY configuration.
           ConfigDB key: PON_SERVICE_CONFIG_PROFILE_FEC_PERF_MON_HIST_DATA|<service-config-profile-name>|<managed-entity-id>.";
        leaf service-config-profile-name {
          type string;
        }
        leaf managed-entity-id {
          type omci-types:omci-uint16;
          description
            "Managed entity ID: This attribute uniquely identifies each instance of this ME. Through an identical ID, this ME is implicitly linked to an instance of the ANI-G or a TWDM channel. (R, set-by-create) (mandatory) (2bytes)";
        }
        leaf threshold-data-1-2-id {
          type omci-types:omci-uint16;
          description
            "Threshold data 1/2 ID: This attribute points to an instance of the threshold data 1 ME that contains PM threshold values. Since no threshold value attribute number exceeds 7, a threshold data 2 ME is optional. (R,W, set-by-create) (mandatory) (2bytes)";
        }
      }
    }
    container PON_SERVICE_CONFIG_PROFILE_GAL_ETHERNET_PERF_MON_HIST_DATA {
      description
        "GAL Ethernet performance monitoring history data, Class Value 276. This ME collects PM data associated with a GEM IW TP when the GEM layer supports an Ethernet service. Instances of this ME are created and deleted by the OLT. For a complete discussion of generic PM architecture, refer to clause I.4. ConfigDB table: PON_SERVICE_CONFIG_PROFILE_GAL_ETHERNET_PERF_MON_HIST_DATA.";
      reference
        "G.988, 9.2.8, GAL Ethernet performance monitoring history data";
      list PON_SERVICE_CONFIG_PROFILE_GAL_ETHERNET_PERF_MON_HIST_DATA_LIST {
        key "service-config-profile-name managed-entity-id";
        description
          "PON_SERVICE_CONFIG_PROFILE_OMCI_CLASS_GAL_ETHERNET_PERF_MON_HIST_DATA_MANAGED_ENTITY configuration.
           ConfigDB key: PON_SERVICE_CONFIG_PROFILE_GAL_ETHERNET_PERF_MON_HIST_DATA|<service-config-profile-name>|<managed-entity-id>.";
        leaf service-config-profile-name {
          type string;
        }
        leaf managed-entity-id {
          type omci-types:omci-uint16;
          description
            "Managed entity ID: This attribute uniquely identifies each instance of this ME. Through an identical ID, this ME is implicitly linked to an instance of the GEM IW TP. (R, set-by-create) (mandatory) (2bytes)";
        }
        leaf threshold-data-1-2-id {
          type omci-types:omci-uint16;
          description
            "Threshold data 1/2 ID: This attribute points to an instance of the threshold data 1 ME that contains PM threshold values. Since no threshold value attribute number exceeds 7, a threshold data 2 ME is optional. (R,W, set-by-create) (mandatory) (2bytes)";
        }
      }
    }
    container PON_SERVICE_CONFIG_PROFILE_GAL_ETHERNET_PROFILE {
      description
        "GAL Ethernet profile, Class Value 272. This ME organizes data that describe the gigabit-capable passive optical network transmission convergence layer (GTC) adaptation layer processing functions of the ONU for Ethernet services. It is used with the GEM IW TP ME. Instances of this ME are created and deleted on request of the OLT. ConfigDB table: PON_SERVICE_CONFIG_PROFILE_GAL_ETHERNET_PROFILE.";
      reference
        "G.988, 9.2.7, GAL Ethernet profile";
      list PON_SERVICE_CONFIG_PROFILE_GAL_ETHERNET_PROFILE_LIST {
        key "service-config-profile-name managed-entity-id";
        description
          "PON_SERVICE_CONFIG_PROFILE_OMCI_CLASS_GAL_ETHERNET_PROFILE_MANAGED_ENTITY configuration.
           ConfigDB key: PON_SERVICE_CONFIG_PROFILE_GAL_ETHERNET_PROFILE|<service-config-profile-name>|<managed-entity-id>.";
        leaf service-config-profile-name {
          type string;
        }
        leaf managed-entity-id {
          type omci-types:omci-uint16;
          description
            "Managed entity ID: This attribute uniquely identifies each instance of this ME. (R, set-by-create) (mandatory) (2bytes)";
        }
        leaf max-gem-payload-size {
          type omci-types:omci-uint16;
          description
            "Maximum GEM payload size: This attribute defines the maximum payload size generated in the associated GEM IW TP ME. (R,W, set-by-create) (mandatory) (2bytes)";
        }
      }
    }
    container PON_SERVICE_CONFIG_PROFILE_GEM_INTERWORKING_TP {
      description
        "GEM interworking termination point, Class Value 266. An instance of this ME represents a point in the ONU where the IW of a bearer service (usually Ethernet) to the GEM layer takes place. At this point, GEM packets are generated from the bearer bit stream (e.g., Ethernet) or the bearer bit stream is reconstructed from GEM packets. Instances of this ME are created and deleted by the OLT. ConfigDB table: PON_SERVICE_CONFIG_PROFILE_GEM_INTERWORKING_TP.";
      reference
        "G.988, 9.2.4, GEM interworking termination point";
      list PON_SERVICE_CONFIG_PROFILE_GEM_INTERWORKING_TP_LIST {
        key "service-config-profile-name managed-entity-id";
        description
          "PON_SERVICE_CONFIG_PROFILE_OMCI_CLASS_GEM_INTERWORKING_TP_MANAGED_ENTITY configuration.
           ConfigDB key: PON_SERVICE_CONFIG_PROFILE_GEM_INTERWORKING_TP|<service-config-profile-name>|<managed-entity-id>.";
        leaf service-config-profile-name {
          type string;
        }
        leaf managed-entity-id {
          type omci-types:omci-uint16;
          description
            "Managed entity ID: This attribute uniquely identifies each instance of this ME. (R, set-by-create) (mandatory) (2bytes)";
        }
        leaf gem-port-network-ctp-pointer {
          type omci-types:omci-uint16;
          description
            "GEM port network CTP connectivity pointer: This attribute points to an instance of the GEM port network CTP. (R,W, set-by-create) (mandatory) (2bytes)";
        }
        leaf interworking-option {
          type omci-types:omci-uint8;
          description
            "Interworking option: This attribute identifies the type of non-GEM function that is being interworked. The options are as follows. 0 Circuit-emulated TDM 1 MAC bridged LAN 2 Reserved 3 Reserved 4 Video return path 5 IEEE 802.1p mapper 6 Downstream broadcast 7 MPLS PW TDM service (R,W, set-by-create) (mandatory) (1byte)";
        }
        leaf service-profile-pointer {
          type omci-types:omci-uint16;
          description
            "Service profile pointer: This attribute points to an instance of a service profile: CES service profile if IW option=0 MAC bridge service profile if IW option=1 Video return path service profile if IW option=4 IEEE 802.1p mapper service profile if IW option=5 Null pointer if IW option=6 CES service profile if IW option=7 (R,W, set-by-create) (mandatory) (2bytes) NOTE The video return path (VRP) service profile is defined in [ITU-T G.984.4].";
        }
        leaf interworking-tp-pointer {
          type omci-types:omci-uint16;
          description
            "Not used 1: This attribute is set to 0 and not used. (R,W, set-by-create) (mandatory) (2bytes)";
        }
        leaf gal-profile-pointer {
          type omci-types:omci-uint16;
          description
            "GAL profile pointer: This attribute points to an instance of the GAL profile. The relationship between the IW option and the related GAL profile is as follows. Interworking option GAL profile type 0 Null pointer 1 GAL Ethernet profile 3 GAL Ethernet profile for data service 4 GAL Ethernet profile for video return path 5 GAL Ethernet profile for IEEE 802.1p mapper 6 Null pointer 7 Null pointer (R,W, set-by-create) (mandatory) (2bytes)";
        }
        leaf gal-loopback-configuration {
          type omci-types:omci-uint8;
          description
            "GAL loopback configuration: This attribute sets the loopback configuration when using GEM mode: 0 No loopback 1 Loopback of downstream traffic after GAL The default value of this attribute is 0. When the IW option is 6 (downstream broadcast), this attribute is not used. (R,W) (mandatory) (1byte)";
        }
      }
    }
    container PON_SERVICE_CONFIG_PROFILE_GEM_PORT_NETWORK_CTP {
      description
        "GEM port network CTP, Class Value 268. This ME represents the termination of a GEM port on an ONU. This ME aggregates connectivity functionality from the network view and alarms from the network element view as well as artefacts from trails. Instances of the GEM port network CTP ME are created and deleted by the OLT. An instance of GEM port network CTP can be deleted only when no GEM IW TP or GEM port network CTP PM history data are associated with it. It is the responsibility of the OLT to make sure that the ONU configuration meets this condition. In ITU-T G.984 systems, when a GEM port network CTP is created, its encryption state is by default not encrypted. If the OLT wishes to configure the GEM port to use encryption, it must send the appropriate PLOAM message. This applies equally to new CTPs and to CTPs that are re-created after an MIB reset. In ITU-T G.987 systems, GEM ports are dynamically encrypted. If it is intended to encrypt the GEM port, the OLT must configure a key ring to be used, and the key must be known to the ONU at run time. ConfigDB table: PON_SERVICE_CONFIG_PROFILE_GEM_PORT_NETWORK_CTP.";
      reference
        "G.988, 9.2.3, GEM port network CTP";
      list PON_SERVICE_CONFIG_PROFILE_GEM_PORT_NETWORK_CTP_LIST {
        key "service-config-profile-name managed-entity-id";
        description
          "PON_SERVICE_CONFIG_PROFILE_OMCI_CLASS_GEM_PORT_NETWORK_CTP_MANAGED_ENTITY configuration.
           ConfigDB key: PON_SERVICE_CONFIG_PROFILE_GEM_PORT_NETWORK_CTP|<service-config-profile-name>|<managed-entity-id>.";
        leaf service-config-profile-name {
          type string;
        }
        leaf managed-entity-id {
          type omci-types:omci-uint16;
          description
            "Managed entity ID: This attribute uniquely identifies each instance of this ME. (R, set-by-create) (mandatory) (2bytes)";
        }
        leaf port-id {
          type omci-types:omci-uint16;
          description
            "Port-ID: This attribute is the port-ID of the GEM port associated with this CTP. (RWSC) (mandatory) (2bytes) NOTE 1 While nothing forbids the existence of several GEM port network CTPs with the same port-ID value, downstream traffic is modelled as being delivered to all such GEM port network CTPs. Be aware of potential difficulties associated with defining downstream flows and aggregating PM statistics.";
        }
        leaf tcont-pointer {
          type omci-types:omci-uint16;
          description
            "T-CONT pointer: This attribute points to a T-CONT instance. (R,W, set-by- create) (mandatory) (2bytes)";
        }
        leaf direction {
          type omci-types:omci-uint8;
          description
            "Direction: This attribute specifies whether the GEM port is used for UNI- to-ANI (1), ANI-to-UNI (2), or bidirectional (3) connection. (R,W, set-by- create) (mandatory) (1byte)";
        }
        leaf traffic-management-pointer-upstream {
          type omci-types:omci-uint16;
          description
            "Traffic management pointer for upstream: If the traffic management option attribute in the ONU-G ME is 0 (priority controlled) or 2 (priority and rate controlled), this pointer specifies the priority queue ME serving this GEM port network CTP. If the traffic management option attribute is 1 (rate controlled), this attribute redundantly points to the T-CONT serving this GEM port network CTP. (R,W, set-by-create) (mandatory) (2bytes)";
        }
        leaf traffic-descriptor-profile-pointer {
          type omci-types:omci-uint16;
          description
            "Traffic descriptor profile pointer for upstream: This attribute points to the instance of the traffic descriptor ME that contains the upstream traffic parameters for this GEM port network CTP. This attribute is used when the traffic management option attribute in the ONU-G ME is 1 (rate controlled), specifying the PIR/PBS to which the upstream traffic is shaped. This attribute is also used when the traffic management option attribute in the ONU-G ME is 2 (priority and rate controlled), specifying the CIR/CBS/PIR/PBS to which the upstream traffic is policed. (R,W, set-by-create) (optional) (2bytes) See also Appendix II.";
        }
        leaf priority-queue-pointer-downstream {
          type omci-types:omci-uint16;
          description
            "Priority queue pointer for downstream: This attribute points to the instance of the priority queue used for this GEM port network CTP in the downstream direction. It is the responsibility of the OLT to provision the downstream pointer in a way that is consistent with the bridge and mapper connectivity. If the pointer is null, downstream queueing is determined by other mechanisms in the ONU. (R,W, set-by-create) (mandatory) (2bytes) NOTE 2 If the GEM port network CTP is associated with more than one UNI (downstream multicast), the downstream priority queue pointer defines a pattern (e.g., queue number 3 for a given UNI) to be replicated (i.e., to queue number 3) at the other affected UNIs.";
        }
        leaf traffic-desc-profile-pointer-downstream {
          type omci-types:omci-uint16;
          description
            "Traffic descriptor profile pointer for downstream: This attribute points to the instance of the traffic descriptor ME that contains the downstream traffic parameters for this GEM port network CTP. This attribute is used when the traffic management option attribute in the ONU-G ME is 1 (rate controlled), specifying the PIR/PBS to which the downstream traffic is shaped. This attribute is also used when the traffic management option attribute in the ONU-G ME is 2 (priority and rate controlled), specifying the CIR/CBS/PIR/PBS to which the downstream traffic is policed. (R,W, set-by-create) (optional) (2bytes) See also Appendix II.";
        }
        leaf encryption-key-ring {
          type omci-types:omci-uint8;
          description
            "Encryption key ring: This attribute is defined in ITU-T G.987 systems only. It specifies whether the associated GEM port is encrypted, and if so, which key ring it uses. (R, W, set-by-create) (optional) (1 byte) 0 (default) No encryption. The downstream key index is ignored, and upstream traffic is transmitted with key index 0. 1 Unicast payload encryption in both directions. Keys are generated by the ONU and transmitted to the OLT via the PLOAM channel. 2 Broadcast (multicast) encryption. Keys are generated by the OLT and distributed via the OMCI. 3 Unicast encryption, downstream only. Keys are generated by the ONU and transmitted to the OLT via the PLOAM channel. Other values are reserved.";
        }
      }
    }
    container PON_SERVICE_CONFIG_PROFILE_GEM_PORT_NETWORK_CTP_PERF_MON_HIST_DATA {
      description
        "GEM port network CTP performance monitoring history data, Class Value 341. This ME collects GEM frame PM data associated with a GEM port network CTP. Instances of this ME are created and deleted by the OLT. NOTE 1 One might expect to find some form of impaired or discarded frame count associated with a GEM port. However, the only impairment that might be detected at the GEM frame level would be a corrupted GEM frame header. In this case, no part of the header could be considered reliable including the port ID. For this reason, there is no impaired or discarded frame count in this ME. NOTE 2 This ME replaces the GEM port performance history data ME and is preferred for new implementations. For a complete discussion of generic PM architecture, refer to clause I.4. ConfigDB table: PON_SERVICE_CONFIG_PROFILE_GEM_PORT_NETWORK_CTP_PERF_MON_HIST_DATA.";
      reference
        "G.988, 9.2.13, GEM port network CTP performance monitoring history data";
      list PON_SERVICE_CONFIG_PROFILE_GEM_PORT_NETWORK_CTP_PERF_MON_HIST_DATA_LIST {
        key "service-config-profile-name managed-entity-id";
        description
          "PON_SERVICE_CONFIG_PROFILE_OMCI_CLASS_GEM_PORT_NETWORK_CTP_PERF_MON_HIST_DATA_MANAGED_ENTITY configuration.
           ConfigDB key: PON_SERVICE_CONFIG_PROFILE_GEM_PORT_NETWORK_CTP_PERF_MON_HIST_DATA|<service-config-profile-name>|<managed-entity-id>.";
        leaf service-config-profile-name {
          type string;
        }
        leaf managed-entity-id {
          type omci-types:omci-uint16;
          description
            "Managed entity ID: This attribute uniquely identifies each instance of this ME. Through an identical ID, this ME is implicitly linked to an instance of the GEM port network CTP. (R, set-by-create) (mandatory) (2bytes)";
        }
        leaf threshold-data-1-2-id {
          type omci-types:omci-uint16;
          description
            "Threshold data 1/2 ID: This attribute points to an instance of the threshold data 1 ME that contains PM threshold values. Since no threshold value attribute number exceeds 7, a threshold data 2 ME is optional. (R,W, set-by-create) (mandatory) (2bytes)";
        }
      }
    }
    container PON_SERVICE_CONFIG_PROFILE_IEEE8021P_MAPPER_SERVICE_PROFILE {
      description
        "IEEE 802.1p mapper service profile, Class Value 130. This ME associates the priorities of IEEE 802.1p [IEEE 802.1D] priority tagged frames with specific connections. This ME directs upstream traffic to the designated GEM ports. Downstream traffic arriving on any of the IEEE 802.1p mapper's GEM ports is directed to the mapper's root TP. Other mechanisms exist to direct downstream traffic, specifically a direct pointer to a downstream queue from the GEM port network CTP. If such an alternative is used, it should be provisioned to be consistent with the flow model of the mapper. Instances of this ME are created and deleted by the OLT. ConfigDB table: PON_SERVICE_CONFIG_PROFILE_IEEE8021P_MAPPER_SERVICE_PROFILE.";
      reference
        "G.988, 9.3.10, IEEE 802.1p mapper service profile";
      list PON_SERVICE_CONFIG_PROFILE_IEEE8021P_MAPPER_SERVICE_PROFILE_LIST {
        key "service-config-profile-name managed-entity-id";
        description
          "PON_SERVICE_CONFIG_PROFILE_OMCI_CLASS_IEEE8021P_MAPPER_SERVICE_PROFILE_MANAGED_ENTITY configuration.
           ConfigDB key: PON_SERVICE_CONFIG_PROFILE_IEEE8021P_MAPPER_SERVICE_PROFILE|<service-config-profile-name>|<managed-entity-id>.";
        leaf service-config-profile-name {
          type string;
        }
        leaf managed-entity-id {
          type omci-types:omci-uint16;
          description
            "Managed entity ID: This attribute uniquely identifies each instance of this ME. (R, set-by-create) (mandatory) (2bytes)";
        }
        leaf tp-pointer {
          type omci-types:omci-uint16;
        }
        leaf interwork-tp-pointer-for-p-bit-priority-0 {
          type omci-types:omci-uint16;
          description
            "Interwork TP pointer for P-bit priority 0: (R,W, set-by-create) (mandatory) (2bytes)";
        }
        leaf interwork-tp-pointer-for-p-bit-priority-1 {
          type omci-types:omci-uint16;
          description
            "Interwork TP pointer for P-bit priority 1: (R,W, set-by-create) (mandatory) (2bytes)";
        }
        leaf interwork-tp-pointer-for-p-bit-priority-2 {
          type omci-types:omci-uint16;
          description
            "Interwork TP pointer for P-bit priority 2: (R,W, set-by-create) (mandatory) (2bytes)";
        }
        leaf interwork-tp-pointer-for-p-bit-priority-3 {
          type omci-types:omci-uint16;
          description
            "Interwork TP pointer for P-bit priority 3: (R,W, set-by-create) (mandatory) (2bytes)";
        }
        leaf interwork-tp-pointer-for-p-bit-priority-4 {
          type omci-types:omci-uint16;
          description
            "Interwork TP pointer for P-bit priority 4: (R,W, set-by-create) (mandatory) (2bytes)";
        }
        leaf interwork-tp-pointer-for-p-bit-priority-5 {
          type omci-types:omci-uint16;
          description
            "Interwork TP pointer for P-bit priority 5: (R,W, set-by-create) (mandatory) (2bytes)";
        }
        leaf interwork-tp-pointer-for-p-bit-priority-6 {
          type omci-types:omci-uint16;
          description
            "Interwork TP pointer for P-bit priority 6: (R,W, set-by-create) (mandatory) (2bytes)";
        }
        leaf interwork-tp-pointer-for-p-bit-priority-7 {
          type omci-types:omci-uint16;
          description
            "Interwork TP pointer for P-bit priority 7: (R,W, set-by-create) (mandatory) (2bytes)";
        }
        leaf unmarked-frame-option {
          type omci-types:omci-uint8;
          description
            "Unmarked frame option: This attribute specifies how the ONU should handle untagged Ethernet frames received across the associated interface. Although it does not alter the frame in any way, the ONU routes the frame as if it were tagged with P bits (PCP field) according to the following code points. 0 Derive implied PCP field from DSCP bits of received frame 1 Set implied PCP field to a fixed value specified by the default P-bit assumption attribute (R,W, set-by-create) (mandatory) (1byte) Untagged downstream frames are passed through the mapper transparently.";
        }
        leaf default-p-bit-assumption {
          type omci-types:omci-uint8;
          description
            "Default P-bit assumption: This attribute is valid when the unmarked frame option attribute is set to 1. In its LSBs, the default P-bit assumption attribute contains the default PCP field to be assumed. The unmodified frame is then directed to the GEM IW TP indicated by the interwork TP pointer mappings. (R,W, set-by-create) (mandatory) (1byte)";
        }
        leaf tp-type {
          type omci-types:omci-uint8;
          description
            "TP type: This attribute identifies the type of TP associated with the mapper. 0 Mapper used for bridging-mapping 1 Mapper directly associated with a PPTP Ethernet UNI 2 Mapper directly associated with an IP host config data or IPv6 host config data ME 3 Mapper directly associated with an Ethernet flow termination point 4 Mapper directly associated with a PPTP xDSL UNI 5 Reserved 6 Mapper directly associated with a PPTP MoCA UNI 7 Mapper directly associated with a virtual Ethernet interface point 8 Mapper directly associated with an IW VCC termination point 9 Mapper directly associated with an EFM bonding group (R,W, set-by-create) (optional) (1byte)";
        }
      }
    }
    container PON_SERVICE_CONFIG_PROFILE_IEEE8021P_MAPPER_SERVICE_PROFILE_DSCP_TO_P_BIT_MAPPING {
      description
        "DSCP to P-bit mapping entry for IEEE 802.1p mapper service profile. ConfigDB table: PON_SERVICE_CONFIG_PROFILE_IEEE8021P_MAPPER_SERVICE_PROFILE_DSCP_TO_P_BIT_MAPPING.";
      list PON_SERVICE_CONFIG_PROFILE_IEEE8021P_MAPPER_SERVICE_PROFILE_DSCP_TO_P_BIT_MAPPING_LIST {
        key "service-config-profile-name id managed-entity-id dscp";
        description
          "PON_SERVICE_CONFIG_PROFILE_OMCI_CLASS_IEEE8021P_MAPPER_SERVICE_PROFILE_MANAGED_ENTITY_DSCP_TO_P_BIT_MAPPING configuration.
           ConfigDB key: PON_SERVICE_CONFIG_PROFILE_IEEE8021P_MAPPER_SERVICE_PROFILE_DSCP_TO_P_BIT_MAPPING|<service-config-profile-name>|<id>|<managed-entity-id>|<dscp>.";
        leaf service-config-profile-name {
          type string;
        }
        leaf id {
          type string;
          description
            "Table entry number starting at '0'";
        }
        leaf managed-entity-id {
          type omci-types:omci-uint16;
          description
            "Managed entity ID: This attribute uniquely identifies each instance of this ME. (R, set-by-create) (mandatory) (2bytes)";
        }
        leaf dscp {
          type omci-types:omci-uint8;
          description
            "DSCP Value";
        }
        leaf priority {
          type omci-types:omci-uint8;
          description
            "P-bit value";
        }
      }
    }
    container PON_SERVICE_CONFIG_PROFILE_IP_HOST_CONFIG_DATA {
      description
        "IP host config data, Class Value 134. The IP host config data configures IPv4 based services offered on the ONU. The ONU automatically creates instances of this ME if IP host services are available. A possible IPv6 stack is supported through the IPv6 host config data ME. In this clause, references to IP addresses are understood to mean IPv4. ConfigDB table: PON_SERVICE_CONFIG_PROFILE_IP_HOST_CONFIG_DATA.";
      reference
        "G.988, 9.4.1, IP host config data";
      list PON_SERVICE_CONFIG_PROFILE_IP_HOST_CONFIG_DATA_LIST {
        key "service-config-profile-name managed-entity-id";
        description
          "PON_SERVICE_CONFIG_PROFILE_OMCI_CLASS_IP_HOST_CONFIG_DATA_MANAGED_ENTITY configuration.
           ConfigDB key: PON_SERVICE_CONFIG_PROFILE_IP_HOST_CONFIG_DATA|<service-config-profile-name>|<managed-entity-id>.";
        leaf service-config-profile-name {
          type string;
        }
        leaf managed-entity-id {
          type omci-types:omci-uint16;
          description
            "Managed entity ID: This attribute uniquely identifies each instance of this ME. The ONU creates as many instances as there are independent IPv4 stacks on the ONU. To facilitate discovery, IP host config data MEs should be numbered from 0 upwards. The ONU should create IP(v4) and IPv6 host config data MEs with separate ME IDs, such that other MEs can use a single TP type attribute to link with either. (R) (mandatory) (2 bytes)";
        }
        leaf ip-options {
          type omci-types:omci-uint8;
          description
            "IP options: This attribute is a bit map that enables or disables IP-related options. The value 1 enables the option while 0 disables it. The default value of this attribute is 0. 0x01 Enable DHCP 0x02 Respond to pings 0x04 Respond to traceroute messages 0x08 Enable IP stack 0x10..0x80 Reserved (R,W) (mandatory) (1byte)";
        }
        leaf onu-identifier {
          type omci-types:omci-string;
          description
            "Onu identifier: A unique ONU identifier string. If set to a non-null value, this string is used instead of the MAC address in retrieving dynamic host configuration protocol (DHCP) parameters. If the string is shorter than 25 characters, it must be null terminated. Its default value is 25 null bytes. (R,W) (mandatory) (25bytes) Several attributes of this ME may be paired together into two categories, manual settings and current values. While the IP stack is disabled, there is no IP connectivity to the external world from this ME instance. While DHCP is disabled, the current values are always the same as the manual settings. While DHCP is enabled, the current values are those assigned by DHCP, or undefined (0) if DHCP has never assigned values.";
        }
        leaf ip-address {
          type omci-types:omci-ipv4-address;
        }
        leaf mask {
          type omci-types:omci-ipv4-address;
        }
        leaf gateway {
          type omci-types:omci-ipv4-address;
        }
        leaf primary-dns {
          type omci-types:omci-ipv4-address;
          description
            "Primary DNS: The manually provisioned IP address of the primary DNS server. The default value of this attribute is the undefined address 0. (R,W) (mandatory) (4bytes)";
        }
        leaf secondary-dns {
          type omci-types:omci-ipv4-address;
          description
            "Secondary DNS: The manually provisioned IP address of the secondary DNS server. The default value of this attribute is the undefined address 0. (R,W) (mandatory) (4bytes)";
        }
        leaf relay-agent-options {
          type omci-types:omci-uint16;
          description
            "Relay agent options: This attribute is a pointer to a large string ME whose content specifies one or more DHCP relay agent options. (R, W) (optional) (2bytes) The meaning and interpretation of the large string's contents are identical to that described in the IP host config data definition in clause 9.4.1.";
        }
      }
    }
    container PON_SERVICE_CONFIG_PROFILE_IP_HOST_PERF_MON_HIST_DATA {
      description
        "IP host performance monitoring history data, Class Value 135. This ME collects PM data related to an IP host. Instances of this ME are created and deleted by the OLT. For a complete discussion of generic PM architecture, refer to clause I.4. ConfigDB table: PON_SERVICE_CONFIG_PROFILE_IP_HOST_PERF_MON_HIST_DATA.";
      reference
        "G.988, 9.4.2, IP host performance monitoring history data";
      list PON_SERVICE_CONFIG_PROFILE_IP_HOST_PERF_MON_HIST_DATA_LIST {
        key "service-config-profile-name managed-entity-id";
        description
          "PON_SERVICE_CONFIG_PROFILE_OMCI_CLASS_IP_HOST_PERF_MON_HIST_DATA_MANAGED_ENTITY configuration.
           ConfigDB key: PON_SERVICE_CONFIG_PROFILE_IP_HOST_PERF_MON_HIST_DATA|<service-config-profile-name>|<managed-entity-id>.";
        leaf service-config-profile-name {
          type string;
        }
        leaf managed-entity-id {
          type omci-types:omci-uint16;
          description
            "Managed entity ID: This attribute uniquely identifies each instance of this ME. Through an identical ID, this ME is implicitly linked to an instance of the IP host configuration data or IPv6 host configuration data ME. (R, set-by-create) (mandatory) (2 bytes)";
        }
        leaf threshold-data-1-2-id {
          type omci-types:omci-uint16;
          description
            "Threshold data 1/2 ID: This attribute points to an instance of the threshold data 1 ME that contains PM threshold values. Since no threshold value attribute number exceeds 7, a threshold data 2 ME is optional. (R,W, set-by-create) (mandatory) (2bytes)";
        }
      }
    }
    container PON_SERVICE_CONFIG_PROFILE_IPV6_HOST_CONFIG_DATA {
      description
        "IPv6 host config data, Class Value 347. The IPv6 host config data configures IPv6 based services offered on the ONU. The ONU automatically creates instances of this ME if IPv6 host services are available. If an IPv4 stack is present, it is independently supported through the IP host config data ME. This ME may be statically provisioned or may derive its parameters from router advertisements (RAs) or DHCPv6. ConfigDB table: PON_SERVICE_CONFIG_PROFILE_IPV6_HOST_CONFIG_DATA.";
      reference
        "G.988, 9.4.5, IPv6 host config data";
      list PON_SERVICE_CONFIG_PROFILE_IPV6_HOST_CONFIG_DATA_LIST {
        key "service-config-profile-name managed-entity-id";
        description
          "PON_SERVICE_CONFIG_PROFILE_OMCI_CLASS_IPV6_HOST_CONFIG_DATA_MANAGED_ENTITY configuration.
           ConfigDB key: PON_SERVICE_CONFIG_PROFILE_IPV6_HOST_CONFIG_DATA|<service-config-profile-name>|<managed-entity-id>.";
        leaf service-config-profile-name {
          type string;
        }
        leaf managed-entity-id {
          type omci-types:omci-uint16;
          description
            "Managed entity ID: This attribute uniquely identifies each instance of this ME. The ONU creates as many instances as there are independent IP stacks on the ONU. To facilitate discovery, IP and IPv6 host config data MEs should be numbered from 0 upwards. The ONU must create IP(v4) and IPv6 host config data MEs with separate ME IDs, such that other MEs can use a single TP type attribute to link with either. (R) (mandatory) (2 bytes)";
        }
        leaf ip-options {
          type omci-types:omci-uint8;
          description
            "IP options: This attribute is a bit map that enables or disables IP-related options. The value 1 enables the option while 0 disables it. The default value of this attribute is 0. 0x01 Enable DHCP 0x02 Respond to pings 0x04 Respond to traceroute messages 0x08 Enable IP stack 0x10..0x80 Reserved (R,W) (mandatory) (1byte)";
        }
        leaf onu-identifier {
          type omci-types:omci-string;
          description
            "Onu identifier: A unique ONU identifier string. If set to a non-null value, this string is used instead of the MAC address in retrieving DHCPv6 parameters. If the string is shorter than 25 characters, it must be null terminated. Its default value is 25 null bytes. (R,W) (mandatory) (25bytes) Several attributes of this ME may be paired together into two categories, manual settings and current values. While this ME instance is administratively locked, it provides no IPv6 connectivity to the external world. Especially if manual provisioning is to be used, it is important that the ME remain locked until provisioning is complete. While autoconfiguration is disabled, the current values are the same as the manual settings. While autoconfiguration is enabled, the current values are those autoconfigured on the basis of RAs, assigned by DHCPv6, or undefined (empty tables) if no values have (yet) been assigned.";
        }
        leaf ipv6-address {
          type omci-types:omci-ipv6-address;
          description
            "IPv6 address: The manually provisioned IPv6 address used for routed IPv6 host services. The address remains valid until reprovisioned, i.e., the preferred and valid lifetimes of this address are infinite. The default value of this attribute is the undefined address 0. (R, W) (mandatory) (16 bytes)";
        }
        leaf default-router {
          type omci-types:omci-ipv6-address;
          description
            "Default router: The manually provisioned IPv6 address of the default router. The default value of this attribute is the undefined address 0. (R,W) (mandatory) (16bytes)";
        }
        leaf primary-dns {
          type omci-types:omci-ipv6-address;
          description
            "Primary DNS: The manually provisioned IPv6 address of the primary DNS server. The default value of this attribute is the undefined address 0. (R,W) (mandatory) (16bytes)";
        }
        leaf secondary-dns {
          type omci-types:omci-ipv6-address;
          description
            "Secondary DNS: The manually provisioned IPv6 address of the secondary DNS server. The default value of this attribute is the undefined address 0. (R,W) (mandatory) (16bytes)";
        }
        leaf on-link-prefix {
          type omci-types:omci-string;
          description
            "On-link prefix: This attribute is the manually provisioned on-link prefix used for destination IPv6 addresses of IPv6 host services. The attribute is structured as follows. Prefix length, number of leading bits in the prefix that are valid (1 byte) Prefix (16 bytes) (R,W) (optional) (17 bytes)";
        }
        leaf relay-agent-options {
          type omci-types:omci-uint16;
          description
            "Relay agent options: This attribute is a pointer to a large string ME whose content specifies one or more DHCP relay agent options. (R, W) (optional) (2bytes) The meaning and interpretation of the large string's contents are identical to that described in the IP host config data definition in clause 9.4.1.";
        }
      }
    }
    container PON_SERVICE_CONFIG_PROFILE_LARGE_STRING {
      description
        "Large string, Class Value 157. The large string ME holds character strings longer than 25bytes, up to 375bytes. It is maintained in up to 15 parts, each part containing 25bytes. If the final part contains fewer than 25bytes, it is terminated by at least one null byte. For example: Or Instances of this ME are created and deleted by the OLT. Under some circumstances, they may also be created by the ONU. To use this ME, the OLT or ONU instantiates the large string ME and then points to the created ME from other ME instances. Systems that maintain the large string should ensure that the large string ME is not deleted while it is still linked. ConfigDB table: PON_SERVICE_CONFIG_PROFILE_LARGE_STRING.";
      reference
        "G.988, 9.12.5, Large string";
      list PON_SERVICE_CONFIG_PROFILE_LARGE_STRING_LIST {
        key "service-config-profile-name managed-entity-id";
        description
          "PON_SERVICE_CONFIG_PROFILE_OMCI_CLASS_LARGE_STRING_MANAGED_ENTITY configuration.
           ConfigDB key: PON_SERVICE_CONFIG_PROFILE_LARGE_STRING|<service-config-profile-name>|<managed-entity-id>.";
        leaf service-config-profile-name {
          type string;
        }
        leaf managed-entity-id {
          type omci-types:omci-uint16;
          description
            "Managed entity ID: This attribute uniquely identifies each instance of this ME. The value 0xFFFF is reserved. When the large string is to be used as an IPv6 address, the value 0 is also reserved. The OLT should create large string MEs starting at 1 (or 0), and numbering upwards. The ONU should create large string MEs starting at 65534 (0xFFFE) and numbering downwards. (R,set-by-create) (mandatory) (2bytes)";
        }
        leaf number-of-parts {
          type omci-types:omci-uint8;
        }
        leaf part-1 {
          type omci-types:omci-string;
          description
            "Part 1, Part 2, Part 3, Part 4, Part 5, Part 6, Part 7, Part 8, Part 9, Part 10, Part 11, Part 12, Part 13, Part 14, Part 15: (R,W) (mandatory) (25bytes * 15 attributes)";
        }
        leaf part-2 {
          type omci-types:omci-string;
          description
            "Part 1, Part 2, Part 3, Part 4, Part 5, Part 6, Part 7, Part 8, Part 9, Part 10, Part 11, Part 12, Part 13, Part 14, Part 15: (R,W) (mandatory) (25bytes * 15 attributes)";
        }
        leaf part-3 {
          type omci-types:omci-string;
          description
            "Part 1, Part 2, Part 3, Part 4, Part 5, Part 6, Part 7, Part 8, Part 9, Part 10, Part 11, Part 12, Part 13, Part 14, Part 15: (R,W) (mandatory) (25bytes * 15 attributes)";
        }
        leaf part-4 {
          type omci-types:omci-string;
          description
            "Part 1, Part 2, Part 3, Part 4, Part 5, Part 6, Part 7, Part 8, Part 9, Part 10, Part 11, Part 12, Part 13, Part 14, Part 15: (R,W) (mandatory) (25bytes * 15 attributes)";
        }
        leaf part-5 {
          type omci-types:omci-string;
          description
            "Part 1, Part 2, Part 3, Part 4, Part 5, Part 6, Part 7, Part 8, Part 9, Part 10, Part 11, Part 12, Part 13, Part 14, Part 15: (R,W) (mandatory) (25bytes * 15 attributes)";
        }
        leaf part-6 {
          type omci-types:omci-string;
          description
            "Part 1, Part 2, Part 3, Part 4, Part 5, Part 6, Part 7, Part 8, Part 9, Part 10, Part 11, Part 12, Part 13, Part 14, Part 15: (R,W) (mandatory) (25bytes * 15 attributes)";
        }
        leaf part-7 {
          type omci-types:omci-string;
          description
            "Part 1, Part 2, Part 3, Part 4, Part 5, Part 6, Part 7, Part 8, Part 9, Part 10, Part 11, Part 12, Part 13, Part 14, Part 15: (R,W) (mandatory) (25bytes * 15 attributes)";
        }
        leaf part-8 {
          type omci-types:omci-string;
          description
            "Part 1, Part 2, Part 3, Part 4, Part 5, Part 6, Part 7, Part 8, Part 9, Part 10, Part 11, Part 12, Part 13, Part 14, Part 15: (R,W) (mandatory) (25bytes * 15 attributes)";
        }
        leaf part-9 {
          type omci-types:omci-string;
          description
            "Part 1, Part 2, Part 3, Part 4, Part 5, Part 6, Part 7, Part 8, Part 9, Part 10, Part 11, Part 12, Part 13, Part 14, Part 15: (R,W) (mandatory) (25bytes * 15 attributes)";
        }
        leaf part-10 {
          type omci-types:omci-string;
          description
            "Part 1, Part 2, Part 3, Part 4, Part 5, Part 6, Part 7, Part 8, Part 9, Part 10, Part 11, Part 12, Part 13, Part 14, Part 15: (R,W) (mandatory) (25bytes * 15 attributes)";
        }
        leaf part-11 {
          type omci-types:omci-string;
          description
            "Part 1, Part 2, Part 3, Part 4, Part 5, Part 6, Part 7, Part 8, Part 9, Part 10, Part 11, Part 12, Part 13, Part 14, Part 15: (R,W) (mandatory) (25bytes * 15 attributes)";
        }
        leaf part-12 {
          type omci-types:omci-string;
          description
            "Part 1, Part 2, Part 3, Part 4, Part 5, Part 6, Part 7, Part 8, Part 9, Part 10, Part 11, Part 12, Part 13, Part 14, Part 15: (R,W) (mandatory) (25bytes * 15 attributes)";
        }
        leaf part-13 {
          type omci-types:omci-string;
          description
            "Part 1, Part 2, Part 3, Part 4, Part 5, Part 6, Part 7, Part 8, Part 9, Part 10, Part 11, Part 12, Part 13, Part 14, Part 15: (R,W) (mandatory) (25bytes * 15 attributes)";
        }
        leaf part-14 {
          type omci-types:omci-string;
          description
            "Part 1, Part 2, Part 3, Part 4, Part 5, Part 6, Part 7, Part 8, Part 9, Part 10, Part 11, Part 12, Part 13, Part 14, Part 15: (R,W) (mandatory) (25bytes * 15 attributes)";
        }
        leaf part-15 {
          type omci-types:omci-string;
          description
            "Part 1, Part 2, Part 3, Part 4, Part 5, Part 6, Part 7, Part 8, Part 9, Part 10, Part 11, Part 12, Part 13, Part 14, Part 15: (R,W) (mandatory) (25bytes * 15 attributes)";
        }
      }
    }
    container PON_SERVICE_CONFIG_PROFILE_MAC_BRIDGE_PERF_MON_HIST_DATA {
      description
        "MAC bridge performance monitoring history data, Class Value 51. This ME collects PM data associated with a MAC bridge. Instances of this ME are created and deleted by the OLT. For a complete discussion of generic PM architecture, refer to clause I.4. ConfigDB table: PON_SERVICE_CONFIG_PROFILE_MAC_BRIDGE_PERF_MON_HIST_DATA.";
      reference
        "G.988, 9.3.3, MAC bridge performance monitoring history data";
      list PON_SERVICE_CONFIG_PROFILE_MAC_BRIDGE_PERF_MON_HIST_DATA_LIST {
        key "service-config-profile-name managed-entity-id";
        description
          "PON_SERVICE_CONFIG_PROFILE_OMCI_CLASS_MAC_BRIDGE_PERF_MON_HIST_DATA_MANAGED_ENTITY configuration.
           ConfigDB key: PON_SERVICE_CONFIG_PROFILE_MAC_BRIDGE_PERF_MON_HIST_DATA|<service-config-profile-name>|<managed-entity-id>.";
        leaf service-config-profile-name {
          type string;
        }
        leaf managed-entity-id {
          type omci-types:omci-uint16;
          description
            "Managed entity ID: This attribute uniquely identifies each instance of this ME. Through an identical ID, this ME is implicitly linked to an instance of the MAC bridge service profile. (R, set-by-create) (mandatory) (2bytes)";
        }
        leaf threshold-data-1-2-id {
          type omci-types:omci-uint16;
          description
            "Threshold data 1/2 ID: This attribute points to an instance of the threshold data 1 ME that contains PM threshold values. Since no threshold value attribute number exceeds 7, a threshold data 2 ME is optional. Since no threshold value attribute number exceeds 7, a threshold data 2 ME is optional. (R,W, set-by- create) (mandatory) (2bytes)";
        }
      }
    }
    container PON_SERVICE_CONFIG_PROFILE_MAC_BRIDGE_PORT_CONFIG_DATA {
      description
        "MAC bridge port configuration data, Class Value 47. This ME models a port on a MAC bridge. Instances of this ME are created and deleted by the OLT. ConfigDB table: PON_SERVICE_CONFIG_PROFILE_MAC_BRIDGE_PORT_CONFIG_DATA.";
      reference
        "G.988, 9.3.4, MAC bridge port configuration data";
      list PON_SERVICE_CONFIG_PROFILE_MAC_BRIDGE_PORT_CONFIG_DATA_LIST {
        key "service-config-profile-name managed-entity-id";
        description
          "PON_SERVICE_CONFIG_PROFILE_OMCI_CLASS_MAC_BRIDGE_PORT_CONFIG_DATA_MANAGED_ENTITY configuration.
           ConfigDB key: PON_SERVICE_CONFIG_PROFILE_MAC_BRIDGE_PORT_CONFIG_DATA|<service-config-profile-name>|<managed-entity-id>.";
        leaf service-config-profile-name {
          type string;
        }
        leaf managed-entity-id {
          type omci-types:omci-uint16;
          description
            "Managed entity ID: This attribute uniquely identifies each instance of this ME. (R, set-by-create) (mandatory) (2bytes)";
        }
        leaf bridge-id-pointer {
          type omci-types:omci-uint16;
          description
            "Bridge ID pointer: This attribute points to an instance of the MAC bridge service profile. (R,W, set-by-create) (mandatory) (2bytes)";
        }
        leaf port-num {
          type omci-types:omci-uint8;
          description
            "Port num: This attribute is the bridge port number. It must be unique among all ports associated with a particular MAC bridge service profile. (R,W, set-by-create) (mandatory) (1byte)";
        }
        leaf tp-type {
          type omci-types:omci-uint8;
          description
            "TP type: This attribute identifies the type of TP associated with this MAC bridge port. Valid values are as follows. 1 Physical path termination point Ethernet UNI 2 Interworking virtual circuit connection (VCC) termination point 3 IEEE 802.1p mapper service profile 4 IP host config data or IPv6 host config data 5 GEM interworking termination point 6 Multicast GEM interworking termination point 7 Physical path termination point xDSL UNI part 1 8 Physical path termination point VDSL UNI 9 Ethernet flow termination point 10 Reserved 11 Virtual Ethernet interface point 12 Physical path termination point MoCA UNI 13 Ethernet in the first mile (EFM) bonding group (R,W, set-by-create) (mandatory) (1byte)";
        }
        leaf tp-pointer {
          type omci-types:omci-uint16;
        }
        leaf port-priority {
          type omci-types:omci-uint16;
          description
            "Port priority: This attribute denotes the priority of the port for use in (rapid) spanning tree algorithms. The range is 0..255. (R,W, set-by-create) (optional) (2bytes)";
        }
        leaf port-path-cost {
          type omci-types:omci-uint16;
          description
            "Port path cost: This attribute specifies the contribution of the port to the path cost towards the spanning tree root bridge. The range is 1..65535. (R,W, set-by-create) (mandatory) (2bytes)";
        }
        leaf port-spanning-tree-ind {
          type omci-types:omci-uint8;
          description
            "Port spanning tree ind: The Boolean value true enables (R)STP LAN topology change detection at this port. The value false disables topology change detection. (R,W, set-by-create) (mandatory) (1byte)";
        }
        leaf deprecated1 {
          type omci-types:omci-uint8;
          description
            "Deprecated 1: This attribute is not used. If present, it should be ignored by both the ONU and the OLT, except as necessary to comply with OMCI message definitions. (R,W, set-by-create) (optional) (1byte)";
        }
        leaf deprecated2 {
          type omci-types:omci-uint8;
          description
            "Deprecated 2: This attribute is not used. If present, it should be ignored by both the ONU and the OLT, except as necessary to comply with OMCI message definitions. (R,W, set-by-create) (1byte) (optional)";
        }
        leaf outbound-td-pointer {
          type omci-types:omci-uint16;
          description
            "Outbound TD pointer: This attribute points to a traffic descriptor that limits the traffic rate leaving the MAC bridge. (R,W) (optional) (2byte)";
        }
        leaf inbound-td-pointer {
          type omci-types:omci-uint16;
          description
            "Inbound TD pointer: This attribute points to a traffic descriptor that limits the traffic rate entering the MAC bridge. (R,W) (optional) (2byte)";
        }
        leaf mac-learning-depth {
          type omci-types:omci-uint8;
          description
            "MAC learning depth: This attribute specifies the maximum number of MAC addresses to be learned by this MAC bridge port. The default value 0 specifies that there is no administratively imposed limit. (R,W, set-by-create) (optional) (1byte) NOTE 2 If this attribute is not zero, its value overrides the value set in the MAC learning depth attribute of the MAC bridge service profile.";
        }
      }
    }
    container PON_SERVICE_CONFIG_PROFILE_MAC_BRIDGE_PORT_PERF_MON_HIST_DATA {
      description
        "MAC bridge port performance monitoring history data, Class Value 52. This ME collects PM data associated with a MAC bridge port. Instances of this ME are created and deleted by the OLT. For a complete discussion of generic PM architecture, refer to clause I.4. ConfigDB table: PON_SERVICE_CONFIG_PROFILE_MAC_BRIDGE_PORT_PERF_MON_HIST_DATA.";
      reference
        "G.988, 9.3.9, MAC bridge port performance monitoring history data";
      list PON_SERVICE_CONFIG_PROFILE_MAC_BRIDGE_PORT_PERF_MON_HIST_DATA_LIST {
        key "service-config-profile-name managed-entity-id";
        description
          "PON_SERVICE_CONFIG_PROFILE_OMCI_CLASS_MAC_BRIDGE_PORT_PERF_MON_HIST_DATA_MANAGED_ENTITY configuration.
           ConfigDB key: PON_SERVICE_CONFIG_PROFILE_MAC_BRIDGE_PORT_PERF_MON_HIST_DATA|<service-config-profile-name>|<managed-entity-id>.";
        leaf service-config-profile-name {
          type string;
        }
        leaf managed-entity-id {
          type omci-types:omci-uint16;
          description
            "Managed entity ID: This attribute uniquely identifies each instance of this ME. Through an identical ID, this ME is implicitly linked to an instance of the MAC bridge port configuration data ME. (R, set-by-create) (mandatory) (2bytes)";
        }
        leaf threshold-data-1-2-id {
          type omci-types:omci-uint16;
          description
            "Threshold data 1/2 ID: This attribute points to an instance of the threshold data 1 ME that contains PM threshold values. Since no threshold value attribute number exceeds 7, a threshold data 2 ME is optional. (R,W, set-by-create) (mandatory) (2bytes)";
        }
      }
    }
    container PON_SERVICE_CONFIG_PROFILE_MAC_BRIDGE_SERVICE_PROFILE {
      description
        "MAC bridge service profile, Class Value 45. This ME models a MAC bridge and its bridge-wide behavior. ConfigDB table: PON_SERVICE_CONFIG_PROFILE_MAC_BRIDGE_SERVICE_PROFILE.";
      reference
        "G.988, 9.3.1, MAC bridge service profile";
      list PON_SERVICE_CONFIG_PROFILE_MAC_BRIDGE_SERVICE_PROFILE_LIST {
        key "service-config-profile-name managed-entity-id";
        description
          "PON_SERVICE_CONFIG_PROFILE_OMCI_CLASS_MAC_BRIDGE_SERVICE_PROFILE_MANAGED_ENTITY configuration.
           ConfigDB key: PON_SERVICE_CONFIG_PROFILE_MAC_BRIDGE_SERVICE_PROFILE|<service-config-profile-name>|<managed-entity-id>.";
        leaf service-config-profile-name {
          type string;
        }
        leaf managed-entity-id {
          type omci-types:omci-uint16;
          description
            "Managed entity ID: This attribute uniquely identifies each instance of this ME. The first byte is the slot ID. In an integrated ONU, this value is 0. The second byte is the bridge group ID. (R, set-by-create) (mandatory) (2bytes)";
        }
        leaf spanning-tree-ind {
          type omci-types:omci-uint8;
          description
            "Spanning tree ind: The Boolean value true specifies that a spanning tree algorithm is enabled. The value false disables (rapid) spanning tree. (R,W, set-by-create) (mandatory) (1byte)";
        }
        leaf learning-ind {
          type omci-types:omci-uint8;
          description
            "Learning ind: The Boolean value true specifies that bridge learning functions are enabled. The value false disables bridge learning. (R,W, set-by-create) (mandatory) (1byte)";
        }
        leaf port-bridging-ind {
          type omci-types:omci-uint8;
          description
            "Port bridging ind: The Boolean value true specifies that bridging between UNI ports is enabled. The value false disables local bridging. (R,W, set-by-create) (mandatory) (1byte)";
        }
        leaf priority {
          type omci-types:omci-uint16;
          description
            "Priority: This attribute specifies the bridge priority in the range 0..65535. The value of this attribute is copied to the bridge priority attribute of the associated MAC bridge configuration data ME. (R,W, set-by-create) (mandatory) (2bytes)";
        }
        leaf max-age {
          type omci-types:omci-uint16;
          description
            "Max age: This attribute specifies the maximum age (in 256ths of a second) of received protocol information before its entry in the spanning tree listing is discarded. The range is 0x0600 to 0x2800 (6..40s) in accordance with [IEEE802.1D]. (R,W, set-by-create) (mandatory) (2bytes)";
        }
        leaf hello-time {
          type omci-types:omci-uint16;
          description
            "Hello time: This attribute specifies how often (in 256ths of a second) the bridge advertises its presence via hello packets, while acting as a root or attempting to become a root. The range is 0x0100 to 0x0A00 (1..10s). (R,W, set-by-create) (mandatory) (2bytes) NOTE [IEEE 802.1D] specifies the compatibility range for hello time to be 1..2s.";
        }
        leaf forward-delay {
          type omci-types:omci-uint16;
          description
            "Forward delay: This attribute specifies the forwarding delay (in 256ths of a second) when the bridge acts as the root. The range is 0x0400 to 0x1E00 (4..30s) in accordance with [IEEE 802.1D]. (R,W, set-by-create) (mandatory) (2bytes)";
        }
        leaf unknown-mac-address-discard {
          type omci-types:omci-uint8;
          description
            "Unknown MAC address discard: The Boolean value true specifies that MAC frames with unknown DAs be discarded. The value false specifies that such frames be forwarded to all allowed ports. (R,W, set-by-create) (mandatory) (1byte)";
        }
        leaf mac-learning-depth {
          type omci-types:omci-uint8;
          description
            "MAC learning depth: This attribute specifies the maximum number of UNI MAC addresses to be learned by the bridge. The default value 0 specifies that there is no administratively imposed limit. (R,W, set-by-create) (optional) (1byte)";
        }
        leaf dynamic-filtering-ageing-time {
          type omci-types:omci-uint32;
          description
            "Dynamic filtering ageing time: This attribute specifies the age of dynamic filtering entries in the bridge database, after which unrefreshed entries are discarded. In accordance with clause 7.9.2 of [IEEE 802.1D] and clause 8.8.3 of [IEEE 802.1Q], the range is 10..1 000 000s, with a resolution of 1s and a default of 300s. The value 0 specifies that the ONU uses its internal default. (R, W, set-by-create) (optional) (4 bytes)";
        }
      }
    }
    container PON_SERVICE_CONFIG_PROFILE_MULTICAST_GEM_INTERWORKING_TP {
      description
        "Multicast GEM interworking termination point, Class Value 281. An instance of this ME represents a point in a G-PON ONU where a multicast service interworks with the GEM layer. At this point, a multicast bit stream is reconstructed from GEM packets. Instances of this ME are created and deleted by the OLT. Multicast interworking GEM modes of operation The default multicast operation of the PON is where all the multicast content streams are carried in one PON layer connection (GEM port). This connection is then specified in the first entry of the IPv4 or IPv6 multicast address table, as the case may be. This single entry also specifies an all-inclusive IP multicast destination address (DA) range (e.g., 224.0.0.0 to 239.255.255.255 in the case of IPv4). The ONU then filters the traffic based on either Ethernet MAC addresses or IP addresses. Theassociated GEM port network CTP ME specifies the GEM port-ID that supports all multicast connections. In the default multicast operation, all multicast content streams are placed in one PON layer connection (GEM port). The OLT sets up a completely conventional model, a pointer from the multicast GEM IW termination to a GEM port network CTP. The OLT configures the GEM port-ID of the GEM port network CTP into the appropriate multicast address table attribute(s), along with the other table fields that specify the range of IP multicast DAs. The ONU accepts the entire multicast stream through the designated GEM port, then filters the traffic based on either the Ethernet MAC address or IP DA. An optional multicast configuration supports separate multicast streams carried over separate PON layer connections, i.e., on separate GEM ports. This permits the ONU to filter multicast streams at the GEM level, which is efficient in hardware, while ignoring other multicast streams that may be of interest to other ONUs on the PON. After configuring the explicit model for the first multicast GEM port, the OLT supports multiple multicast GEM ports by then configuring additional entries into the multicast address table(s), entries with different GEM port-IDs. The OMCI model is defined such that these ports are implicitly grouped together and served by the single explicit GEM port network CTP. No additional GEM network CTPs need be created or linked for the additional GEM ports. Several multicast GEM IW TPs can exist, each linked to separate bridge ports or mappers to serve different communities of interest in a complex ONU. Discovery of multicast support The OLT uses the multicast GEM IW TP entity as the means to discover the ONU's multicast capability. This entity is mandatory if multicast is supported by the ONU. If the OLT attempts to create this entity on an ONU that does not support multicast, the create command fails. The create or set command also fails if the OLT attempts to exploit optional features that the ONU does not support, e.g., in attempting to write a multicast address table with more than a single entry or to create multiple multicast GEM IW TPs. This ME is defined by a similarity to the unicast GEM IW TP, and a number of its attributes are not meaningful in a multicast context. These attributes are set to 0 and not used, as indicated in the following. ConfigDB table: PON_SERVICE_CONFIG_PROFILE_MULTICAST_GEM_INTERWORKING_TP.";
      reference
        "G.988, 9.2.5, Multicast GEM interworking termination point";
      list PON_SERVICE_CONFIG_PROFILE_MULTICAST_GEM_INTERWORKING_TP_LIST {
        key "service-config-profile-name managed-entity-id";
        description
          "PON_SERVICE_CONFIG_PROFILE_OMCI_CLASS_MULTICAST_GEM_INTERWORKING_TP_MANAGED_ENTITY configuration.
           ConfigDB key: PON_SERVICE_CONFIG_PROFILE_MULTICAST_GEM_INTERWORKING_TP|<service-config-profile-name>|<managed-entity-id>.";
        leaf service-config-profile-name {
          type string;
        }
        leaf managed-entity-id {
          type omci-types:omci-uint16;
          description
            "Managed entity ID: This attribute uniquely identifies each instance of this ME. The value 0xFFFF is reserved. (R, set-by-create) (mandatory) (2bytes)";
        }
        leaf gem-port-network-ctp-pointer {
          type omci-types:omci-uint16;
          description
            "GEM port network CTP connectivity pointer: This attribute points to an instance of the GEM port network CTP that is associated with this multicast GEM IW TP. (R,W, set-by-create) (mandatory) (2bytes)";
        }
        leaf interworking-option {
          type omci-types:omci-uint8;
          description
            "Interworking option: This attribute identifies the type of non-GEM function that is being interworked. The option can be as follows. 0 This value is a 'no-op' or 'don't care'. It should be used when the multicast GEM IW TP is associated with several functions of different types. It can optionally be used in all cases, since the necessary information is available elsewhere. The previous code points are retained for backward compatibility: 1 MAC bridged LAN 3 Reserved 5 IEEE 802.1p mapper (R,W, set-by-create) (mandatory) (1byte)";
        }
        leaf service-profile-pointer {
          type omci-types:omci-uint16;
          description
            "Service profile pointer: This attribute is set to 0 and not used. For backward compatibility, it may also be set to point to a MAC bridge service profile or IEEE 802.1p mapper service profile. (R,W, set-by-create) (mandatory) (2bytes)";
        }
        leaf interworking-tp-pointer {
          type omci-types:omci-uint16;
          description
            "Not used 1: This attribute is set to 0 and not used. (R,W, set-by-create) (mandatory) (2bytes)";
        }
        leaf gal-profile-pointer {
          type omci-types:omci-uint16;
          description
            "GAL profile pointer: This attribute is set to 0 and not used. For backward compatibility, it may also be set to point to a GAL Ethernet profile. (R,W, set-by-create) (mandatory) (2bytes)";
        }
        leaf gal-loopback-configuration {
          type omci-types:omci-uint8;
          description
            "Not used 2: This attribute is set to 0 and not used. (R,W, set-by-create) (mandatory) (1byte)";
        }
      }
    }
    container PON_SERVICE_CONFIG_PROFILE_MULTICAST_GEM_INTERWORKING_TP_IPV4_MULTICAST_ADDRESS {
      description
        "IPv4 multicast address table entry for Multicast GEM interworking termination point. ConfigDB table: PON_SERVICE_CONFIG_PROFILE_MULTICAST_GEM_INTERWORKING_TP_IPV4_MULTICAST_ADDRESS.";
      list PON_SERVICE_CONFIG_PROFILE_MULTICAST_GEM_INTERWORKING_TP_IPV4_MULTICAST_ADDRESS_LIST {
        key "service-config-profile-name id managed-entity-id ipv4-multicast-address-table-entry-id";
        description
          "PON_SERVICE_CONFIG_PROFILE_OMCI_CLASS_MULTICAST_GEM_INTERWORKING_TP_MANAGED_ENTITY_IPV4_MULTICAST_ADDRESS configuration.
           ConfigDB key: PON_SERVICE_CONFIG_PROFILE_MULTICAST_GEM_INTERWORKING_TP_IPV4_MULTICAST_ADDRESS|<service-config-profile-name>|<id>|<managed-entity-id>|<ipv4-multicast-address-table-entry-id>.";
        leaf service-config-profile-name {
          type string;
        }
        leaf id {
          type string;
          description
            "Table entry number starting at '0'";
        }
        leaf managed-entity-id {
          type omci-types:omci-uint16;
          description
            "Managed entity ID: This attribute uniquely identifies each instance of this ME. The value 0xFFFF is reserved. (R, set-by-create) (mandatory) (2bytes)";
        }
        leaf ipv4-multicast-address-table-entry-id {
          type uint8;
        }
        leaf gem-port-id {
          type omci-types:omci-uint16;
          description
            "gem port id";
        }
        leaf secondary-key {
          type omci-types:omci-uint16;
          description
            "secondary key";
        }
        leaf ip-multicast-da-range-start {
          type omci-types:omci-ipv4-address;
          description
            "ip multicast da range start";
        }
        leaf ip-multicast-da-range-stop {
          type omci-types:omci-ipv4-address;
          description
            "ip multicast da range stop";
        }
      }
    }
    container PON_SERVICE_CONFIG_PROFILE_MULTICAST_GEM_INTERWORKING_TP_IPV6_MULTICAST_ADDRESS {
      description
        "IPv6 multicast address table entry for Multicast GEM interworking termination point. ConfigDB table: PON_SERVICE_CONFIG_PROFILE_MULTICAST_GEM_INTERWORKING_TP_IPV6_MULTICAST_ADDRESS.";
      list PON_SERVICE_CONFIG_PROFILE_MULTICAST_GEM_INTERWORKING_TP_IPV6_MULTICAST_ADDRESS_LIST {
        key "service-config-profile-name id managed-entity-id ipv6-multicast-address-table-entry-id";
        description
          "PON_SERVICE_CONFIG_PROFILE_OMCI_CLASS_MULTICAST_GEM_INTERWORKING_TP_MANAGED_ENTITY_IPV6_MULTICAST_ADDRESS configuration.
           ConfigDB key: PON_SERVICE_CONFIG_PROFILE_MULTICAST_GEM_INTERWORKING_TP_IPV6_MULTICAST_ADDRESS|<service-config-profile-name>|<id>|<managed-entity-id>|<ipv6-multicast-address-table-entry-id>.";
        leaf service-config-profile-name {
          type string;
        }
        leaf id {
          type string;
          description
            "Table entry number starting at '0'";
        }
        leaf managed-entity-id {
          type omci-types:omci-uint16;
          description
            "Managed entity ID: This attribute uniquely identifies each instance of this ME. The value 0xFFFF is reserved. (R, set-by-create) (mandatory) (2bytes)";
        }
        leaf ipv6-multicast-address-table-entry-id {
          type uint8;
        }
        leaf gem-port-id {
          type omci-types:omci-uint16;
          description
            "gem port id";
        }
        leaf secondary-key {
          type omci-types:omci-uint16;
          description
            "secondary key";
        }
        leaf lsb-ip-multicast-da-range-start {
          type omci-types:omci-string;
          description
            "lsb ip multicast da range start";
        }
        leaf lsb-ip-multicast-da-range-stop {
          type omci-types:omci-string;
          description
            "lsb ip multicast da range stop";
        }
        leaf msb-ip-multicast-da {
          type omci-types:omci-string;
          description
            "msb ip multicast da";
        }
      }
    }
    container PON_SERVICE_CONFIG_PROFILE_OLT_G {
      description
        "OLT-G, Class Value 131. This optional ME identifies the OLT to which an ONU is connected. This ME provides a way for the ONU to configure itself for operability with a particular OLT. It also provides a way for the OLT to communicate the time of day to the ONU. An ONU that supports this ME automatically creates an instance of it. Immediately following the start-up phase, the OLT should set the ONU to the desired configuration. Interpretation of the OLT vendor ID, equipment ID and version attributes is a matter for negotiation between the two vendors involved. ConfigDB table: PON_SERVICE_CONFIG_PROFILE_OLT_G.";
      reference
        "G.988, 9.12.2, OLT-G";
      list PON_SERVICE_CONFIG_PROFILE_OLT_G_LIST {
        key "service-config-profile-name managed-entity-id";
        description
          "PON_SERVICE_CONFIG_PROFILE_OMCI_CLASS_OLT_G_MANAGED_ENTITY configuration.
           ConfigDB key: PON_SERVICE_CONFIG_PROFILE_OLT_G|<service-config-profile-name>|<managed-entity-id>.";
        leaf service-config-profile-name {
          type string;
        }
        leaf managed-entity-id {
          type omci-types:omci-uint16;
          description
            "Managed entity ID: This attribute uniquely identifies each instance of this ME. There is only one instance, number 0. (R) (mandatory) (2bytes)";
        }
        leaf olt-vendor-id {
          type omci-types:omci-string;
          description
            "OLT vendor ID: This attribute identifies the OLT vendor. It is the same as the four most significant bytes of an ONU serial number specified in the respective TC layer specification. Upon instantiation, this attribute comprises all spaces. (R,W) (mandatory) (4bytes)";
        }
        leaf equipment-id {
          type omci-types:omci-string;
          description
            "Equipment ID: This attribute may be used to identify the specific type of OLT. The default value of all spaces indicates that equipment ID information is not available or applicable to the OLT being represented. (R,W) (mandatory) (20bytes)";
        }
        leaf version {
          type omci-types:omci-string;
          description
            "Version: This attribute identifies the version of the OLT as defined by the vendor. The default left-justified ASCII string '0' (padded with trailing nulls) indicates that version information is not available or applicable to the OLT being represented. (R,W) (mandatory) (14bytes)";
        }
        leaf time-of-day {
          type omci-types:omci-string;
          description
            "Time of day information: This attribute provides the information required to achieve time of day synchronization between a reference clock at the OLT and a local clock at the ONU. This attribute comprises two fields: the first field (4bytes) is the sequence number of the specified GEM superframe. The second field (10bytes) is TstampN as defined in clause 10.4.6 of [ITU-T G.984.3], clause 13.2 of [ITU-T G.987.3] and clause 13.2 of [ITU-T G.989.3], using the timestamp format of clause 5.3.3 of [IEEE 1588]. The value 0 in all bytes is reserved as a null value. (R,W) (optional) (14bytes) NOTE In ITU-T G.987/ITU-T G.989 systems, the superframe count field of the time of day information attribute contains the 32 LSBs of the actual counter.";
        }
      }
    }
    container PON_SERVICE_CONFIG_PROFILE_ONU2_G {
      description
        "ONU2-G, Class Value 257. This ME contains additional attributes associated with a PON ONU. The ONU automatically creates an instance of this ME. Its attributes are populated according to data within the ONU itself. This ME is the same as the ONT2-G of [ITU-T G.984.4], with extensions. ConfigDB table: PON_SERVICE_CONFIG_PROFILE_ONU2_G.";
      reference
        "G.988, 9.1.2, ONU2-G";
      list PON_SERVICE_CONFIG_PROFILE_ONU2_G_LIST {
        key "service-config-profile-name managed-entity-id";
        description
          "PON_SERVICE_CONFIG_PROFILE_OMCI_CLASS_ONU2_G_MANAGED_ENTITY configuration.
           ConfigDB key: PON_SERVICE_CONFIG_PROFILE_ONU2_G|<service-config-profile-name>|<managed-entity-id>.";
        leaf service-config-profile-name {
          type string;
        }
        leaf managed-entity-id {
          type omci-types:omci-uint16;
          description
            "Managed entity ID: This attribute uniquely identifies each instance of this ME. There is only one instance, number 0. (R) (mandatory) (2bytes)";
        }
        leaf security-mode {
          type omci-types:omci-uint8;
        }
        leaf current-connectivity-mode {
          type omci-types:omci-uint8;
          description
            "Current connectivity mode: This attribute specifies the Ethernet connectivity model that the OLT wishes to use. The following code points are defined. NOTE 2 It is not implied that an ONU supports a given connectivity model only when that model is explicitly selected by this attribute. The ONU is free to support additional models at any and all times. (R, W) (optional) (1 byte)";
        }
        leaf priority-queue-scale-factor {
          type omci-types:omci-uint16;
          description
            "Priority queue scale factor: If this optional attribute is implemented, it specifies the scale factor of several attributes of the priority queue ME of clause9.2.10. The default value of this attribute is 1. (R, W) (optional) (2bytes) NOTE 3 Some legacy implementations may take the queue scale factor from the GEM block length attribute of the ANI-G ME. That option is discouraged in new implementations.";
        }
      }
    }
    container PON_SERVICE_CONFIG_PROFILE_ONU_G {
      description
        "ONU-G, Class Value 256. This ME represents the ONU as equipment. The ONU automatically creates an instance of this ME. It assigns values to read-only attributes according to data within the ONU itself. This ME has evolved from the ONT-G of [ITU-T G.984.4]. ConfigDB table: PON_SERVICE_CONFIG_PROFILE_ONU_G.";
      reference
        "G.988, 9.1.1, ONU-G";
      list PON_SERVICE_CONFIG_PROFILE_ONU_G_LIST {
        key "service-config-profile-name managed-entity-id";
        description
          "PON_SERVICE_CONFIG_PROFILE_OMCI_CLASS_ONU_G_MANAGED_ENTITY configuration.
           ConfigDB key: PON_SERVICE_CONFIG_PROFILE_ONU_G|<service-config-profile-name>|<managed-entity-id>.";
        leaf service-config-profile-name {
          type string;
        }
        leaf managed-entity-id {
          type omci-types:omci-uint16;
          description
            "Managed entity ID: This attribute uniquely identifies each instance of this ME. There is only one instance, number 0. (R) (mandatory) (2bytes)";
        }
        leaf battery-backup {
          type omci-types:omci-uint8;
        }
        leaf administrative-state {
          type omci-types:omci-uint8;
          description
            "Administrative state: This attribute locks (1) and unlocks (0) the functions performed by the ONU as an entirety. Administrative state is further described in clause A.1.6. (R,W) (mandatory) (1byte)";
        }
        leaf credentials-status {
          type omci-types:omci-uint8;
          description
            "Credentials status: This attribute permits the OLT to signal to the ONU whether its credentials are valid or not. The behaviour of the ONU is not specified, but might, for example, include displaying an error screen to the user. (R, W) (optional) (1byte) Values include: 0 Initial state, status indeterminate 1 Successful authentication 2 Logical ONU ID (LOID) error 3 Password error 4 Duplicate LOID Other values are reserved.";
        }
      }
    }
    container PON_SERVICE_CONFIG_PROFILE_ONU_OPERATIONAL_PERF_MON_HIST_DATA {
      description
        "ONU operational performance monitoring history data, Class Value 459. This managed entity collects performance monitoring data associated with the ONU instances of this managed entity are created and deleted by the OLT. For a complete discussion of generic PM architecture, refer to clause I.4. ConfigDB table: PON_SERVICE_CONFIG_PROFILE_ONU_OPERATIONAL_PERF_MON_HIST_DATA.";
      reference
        "G.988, 9.1.18, ONU operational performance monitoring history data";
      list PON_SERVICE_CONFIG_PROFILE_ONU_OPERATIONAL_PERF_MON_HIST_DATA_LIST {
        key "service-config-profile-name managed-entity-id";
        description
          "PON_SERVICE_CONFIG_PROFILE_OMCI_CLASS_ONU_OPERATIONAL_PERF_MON_HIST_DATA_MANAGED_ENTITY configuration.
           ConfigDB key: PON_SERVICE_CONFIG_PROFILE_ONU_OPERATIONAL_PERF_MON_HIST_DATA|<service-config-profile-name>|<managed-entity-id>.";
        leaf service-config-profile-name {
          type string;
        }
        leaf managed-entity-id {
          type omci-types:omci-uint16;
          description
            "Managed entity ID: This attribute uniquely identifies each instance of this ME. There is only one instance, number 0. (R) (mandatory) (2 bytes)";
        }
        leaf threshold-data-1-2-id {
          type omci-types:omci-uint16;
          description
            "Threshold data 1/2 ID: This attribute points to an instance of the threshold data 1 managed entity that contains PM threshold values. Since no threshold value attribute number exceeds 7, a threshold data 2 ME is optional. (R, W, Set by create) (mandatory) (2 bytes)";
        }
      }
    }
    container PON_SERVICE_CONFIG_PROFILE_PPTP_RS232_RS485_UNI {
      description
        "Physical path termination point RS232/RS485 UNI, Class Value 401. This ME represents an RS232/RS485 UNI in the ONU, where physical paths terminate and physical path level functions are performed. The ONU automatically creates an instance of this ME per port as follows. When the ONU has RS232/RS485 ports built into its factory configuration. When a cardholder is provisioned to expect a circuit pack of RS232/RS485 type. When a cardholder provisioned for plug and play is equipped with a circuit pack of RS232/RS485 type. Note that the installation of a plug and play card may indicate the presence of RS232/RS485 ports via equipment ID as well as its type, and indeed may cause the ONU to instantiate a port-mapping package that specifies RS232/RS485 ports. The ONU automatically deletes instances of this ME when a cardholder is neither provisioned to expect a RS232/RS485 circuit pack, nor is equipped with a RS232/RS485 circuit pack. ConfigDB table: PON_SERVICE_CONFIG_PROFILE_PPTP_RS232_RS485_UNI.";
      reference
        "G.988, 9.15.1, Physical path termination point RS232/RS485 UNI";
      list PON_SERVICE_CONFIG_PROFILE_PPTP_RS232_RS485_UNI_LIST {
        key "service-config-profile-name managed-entity-id";
        description
          "PON_SERVICE_CONFIG_PROFILE_OMCI_CLASS_PPTP_RS232_RS485_UNI_MANAGED_ENTITY configuration.
           ConfigDB key: PON_SERVICE_CONFIG_PROFILE_PPTP_RS232_RS485_UNI|<service-config-profile-name>|<managed-entity-id>.";
        leaf service-config-profile-name {
          type string;
        }
        leaf managed-entity-id {
          type omci-types:omci-uint16;
          description
            "Managed entity ID: This attribute uniquely identifies each instance of this ME. This 2byte number is directly associated with the physical position of the UNI. The first byte is the slot ID (defined in clause 9.1.5). The second byte is the port ID, with range 1..255. (R) (mandatory) (2bytes)";
        }
        leaf administrative-state {
          type omci-types:omci-uint8;
          description
            "Administrative state: This attribute locks (1) and unlocks (0) the functions performed by this ME. Administrative state is further described in clause A.1.6. (R,W) (mandatory) (1byte)";
        }
        leaf port-mode {
          type omci-types:omci-uint8;
          description
            "Port mode: This attribute indicates the working mode of the RS232/RS485 controller chipset. Valid values are as follows. 0 half-duplex 1 full duplex (mandatory) (1byte)";
        }
        leaf baud-rate {
          type omci-types:omci-uint8;
          description
            "Baud_rate: This attribute specifies the working baud rate of RS232/RS485 port. Valid values are as follows. 0 300 bit/s 1 600 bit/s 2 1200 bit/s 3 2400 bit/s 4 4800 bit/s 5 9600 bit/s 6 19200 bit/s 7 38400 bit/s 8 43000 bit/s 9 56000 bit/s 10 57600 bit/s 11 115200 bit/s (R,W, set-by-create) (mandatory) (1byte)";
        }
        leaf data-bits {
          type omci-types:omci-uint8;
          description
            "Data_bits: This attribute specifies the bits of the data. Valid values are as follows. 5 5 bits 6 6 bits 7 7 bits 8 8 bits (R,W, set-by-create) (mandatory) (1byte)";
        }
        leaf parity {
          type omci-types:omci-uint8;
          description
            "Parity: This attribute specifies the parity of the data. Valid values are as follows. 0 no parity 1 odd parity 2 even parity (R,W, set-by-create) (mandatory) (1byte)";
        }
        leaf stop-bits {
          type omci-types:omci-uint8;
          description
            "Stop_bits: This attribute specifies the number of stop bits of the data. Valid values are as follows. 1 1 bit 2 2 bits (R,W, set-by-create) (mandatory) (1byte)";
        }
        leaf flow-control {
          type omci-types:omci-uint8;
          description
            "Flow_control: This attribute specifies the flow control of the data. Valid values are as follows. 0 no flow control 1 hardware flow control (RTS/CTS) 2 software flow control (Xon/Xoff) (R,W, set-by-create) (mandatory) (1byte)";
        }
      }
    }
    container PON_SERVICE_CONFIG_PROFILE_PRIORITY_QUEUE {
      description
        "Priority queue, Class Value 277. This ME models ONU queue behavior and queue scheduling relationships for upstream and downstream traffic. ConfigDB table: PON_SERVICE_CONFIG_PROFILE_PRIORITY_QUEUE.";
      reference
        "G.988, 9.2.10, Priority queue";
      list PON_SERVICE_CONFIG_PROFILE_PRIORITY_QUEUE_LIST {
        key "service-config-profile-name managed-entity-id";
        description
          "PON_SERVICE_CONFIG_PROFILE_OMCI_CLASS_PRIORITY_QUEUE_MANAGED_ENTITY configuration.
           ConfigDB key: PON_SERVICE_CONFIG_PROFILE_PRIORITY_QUEUE|<service-config-profile-name>|<managed-entity-id>.";
        leaf service-config-profile-name {
          type string;
        }
        leaf managed-entity-id {
          type omci-types:omci-uint16;
          description
            "Managed entity ID: This attribute uniquely identifies each instance of this ME. The MSB represents the direction (1: upstream, 0:downstream). The 15 LSBs represent a queue ID. The queue ID is numbered in ascending order by the ONU itself. It is strongly encouraged that the queue ID be formulated to simplify finding related queues. One way to do this is to number the queues such that the related port attributes are in ascending order (for the downstream and upstream queues separately). The range of downstream queue ids is 0 to 0x7FFF and the range of upstream queue ids is 0x8000 to 0xFFFF. (R) (mandatory) (2bytes)";
        }
        leaf allocated-queue-size {
          type omci-types:omci-uint16;
          description
            "Allocated queue size: This attribute identifies the allocated size of this queue, in bytes, scaled by the priority queue scale factor attribute of the ONU2-G. (R, W) (mandatory) (2 bytes)";
        }
        leaf discard-block-counter-reset-interval {
          type omci-types:omci-uint16;
          description
            "Discard-block counter reset interval: This attribute represents the interval in milliseconds at which the counter resets itself. (R,W) (optional) (2bytes)";
        }
        leaf threshold-value-for-discarded-blocks {
          type omci-types:omci-uint16;
          description
            "Threshold value for discarded blocks due to buffer overflow: This attribute specifies the threshold for the number of bytes (scaled by the priority queue scale factor attribute of the ONU2-G) discarded on this queue due to buffer overflow. Its value controls the declaration of the block loss alarm. (R, W) (optional) (2bytes)";
        }
        leaf related-port {
          type omci-types:omci-uint32;
          description
            "Related port: This attribute represents the slot, port/T-CONT and priority information associated with the instance of priority queue ME. This attribute comprises 4bytes. In the upstream direction, the first 2bytes are the ME ID of the associated T-CONT, the first byte of which is a slot number, the second byte a T-CONT number. In the downstream direction, the first byte is the slot number and the second byte is the port number of the queue's destination port. The last 2bytes represent the priority of this queue. The range of priority is 0 to 0x0FFF. The value 0 indicates the highest priority and 0x0FFF indicates the lowest priority. The priority field is meaningful if multiple priority queues are associated with a T-CONT or traffic scheduler whose scheduling discipline is strict priority. (R, W) (mandatory) (4 bytes) NOTE 3 If flexible port configuration is supported, the related port attribute is meaningful only if the traffic scheduler pointer attribute value is null. Otherwise, the related port attribute is ignored. NOTE 4 The related port attribute is read-only, unless otherwise specified by the QoS configuration flexibility attribute of the ONU2-G ME. If port flexibility is supported, the second byte, the port or T-CONT number, may be changed. If priority flexibility is supported, the third and fourth bytes may be changed. The OMCI set command must contain 4bytes to match the attribute size, but the ONU must ignore all bytes that are not specified to be flexible. If flexible configuration is not supported, the ONU should reject an attempt to set the related port with a parameter error result-reason code.";
        }
        leaf traffic-scheduler-pointer {
          type omci-types:omci-uint16;
          description
            "Traffic scheduler pointer: This attribute points to the traffic scheduler ME instance that is associated with this priority queue. This pointer is used when this priority queue is connected with a traffic scheduler. The default value is a null pointer (0). (R, W) (mandatory) (2 bytes) NOTE 5 When the QoS configuration flexibility attribute of the ONU2-G ME allows flexible assignment of the traffic scheduler, the OLT may configure the traffic scheduler pointer to refer to any traffic scheduler in the same slot. If traffic scheduler flexibility is not permitted by the QoS configuration flexibility attribute, the OLT may use the traffic scheduler pointer attribute only by pointing to another traffic scheduler ME that is associated with the same T-CONT as the priority queue itself. The ONU should reject an attempt to violate these conditions with a parameter error result-reason code.";
        }
        leaf weight {
          type omci-types:omci-uint8;
          description
            "Weight: This attribute represents weight for WRR scheduling. At a given priority level, capacity is distributed to non-empty queues in proportion to their weights. In the upstream direction, this weight is meaningful if several priority queues are associated with a traffic scheduler or T-CONT whose policy is WRR. In the downstream direction, this weight is used by a UNI in a WRR fashion. Upon ME instantiation, the ONU sets this attribute to 1. (R,W) (mandatory) (1byte)";
        }
        leaf back-pressure-operation {
          type omci-types:omci-uint16;
          description
            "Back pressure operation: This attribute enables (0) or disables (1) back pressure operation. Its default value is 0. (R,W) (mandatory) (2bytes)";
        }
        leaf back-pressure-time {
          type omci-types:omci-uint32;
          description
            "Back pressure time: This attribute specifies the duration in microseconds of the back-pressure signal. It can be used as a pause time for an Ethernet UNI. Upon ME instantiation, the ONU sets this attribute to 0. (R,W) (mandatory) (4bytes)";
        }
        leaf back-pressure-occur-queue-threshold {
          type omci-types:omci-uint16;
          description
            "Back pressure occur queue threshold: This attribute identifies the threshold queue occupancy, in bytes, scaled by the priority queue scale factor attribute of the ONU2-G, to start sending a back-pressure signal. (R, W) (mandatory) (2bytes)";
        }
        leaf back-pressure-clear-queue-threshold {
          type omci-types:omci-uint16;
          description
            "Back pressure clear queue threshold: This attribute identifies the threshold queue occupancy, in bytes, scaled by the priority queue scale factor attribute of the ONU2-G, to stop sending a back-pressure signal. (R, W) (mandatory) (2bytes)";
        }
        leaf packet-drop-max-p {
          type omci-types:omci-uint16;
          description
            "Packet drop max_p: This attribute is a composite of two 1byte values, the probability of dropping a coloured packet when the queue occupancy lies just below the maximum threshold for packets of that colour. The first value is the green packet max_p, and the second value is the yellow packet max_p. The probability, max_p, is determined by adding one to the unsigned value (0..255) of this attribute and dividing the result by 256. The default for each value is 255. (R,W) (optional) (2bytes)";
        }
        leaf queue-drop-w-q {
          type omci-types:omci-uint8;
          description
            "Queue drop w_q: This attribute determines the averaging coefficient, w_q, as described in [b-Floyd]. The averaging coefficient, w_q, is equal to 2-Queue_drop_w_q. For example, when queue drop_w_q has the value 9, the averaging coefficient, w_q, is 1/512= 0.0019. The default value is 9. (R,W) (optional) (1byte)";
        }
        leaf drop-precedence-colour-marking {
          type omci-types:omci-uint8;
          description
            "Drop precedence colour marking: This attribute specifies how drop precedence is marked on ingress packets to the priority queue. The default value is 0. 0 No marking (treat all packets as green) 1 Internal marking (from traffic descriptor ME) 2 DEI [IEEE 802.1ad] 3 PCP 8P0D [IEEE 802.1ad] 4 PCP 7P1D [IEEE 802.1ad] 5 PCP 6P2D [IEEE 802.1ad] 6 PCP 5P3D [IEEE 802.1ad] 7 DSCP AF class [IETF RFC 2597] (R,W) (optional) (1byte)";
        }
      }
    }
    container PON_SERVICE_CONFIG_PROFILE_PRIORITY_QUEUE_PACKET_DROP_QUEUE_THRESHOLD {
      description
        "Packet drop queue thresholds for Priority queue. This structure defines green/yellow minimum and maximum queue occupancy thresholds used for drop decisions. ConfigDB table: PON_SERVICE_CONFIG_PROFILE_PRIORITY_QUEUE_PACKET_DROP_QUEUE_THRESHOLD.";
      list PON_SERVICE_CONFIG_PROFILE_PRIORITY_QUEUE_PACKET_DROP_QUEUE_THRESHOLD_LIST {
        key "service-config-profile-name managed-entity-id";
        description
          "PON_SERVICE_CONFIG_PROFILE_OMCI_CLASS_PRIORITY_QUEUE_MANAGED_ENTITY_PACKET_DROP_QUEUE_THRESHOLD configuration.
           ConfigDB key: PON_SERVICE_CONFIG_PROFILE_PRIORITY_QUEUE_PACKET_DROP_QUEUE_THRESHOLD|<service-config-profile-name>|<managed-entity-id>.";
        leaf service-config-profile-name {
          type string;
        }
        leaf managed-entity-id {
          type leafref {
            path "/sp:sonic-pon/sp:PON_SERVICE_CONFIG_PROFILE_PRIORITY_QUEUE/sp:PON_SERVICE_CONFIG_PROFILE_PRIORITY_QUEUE_LIST/sp:managed-entity-id";
          }
          description
            "References PON_SERVICE_CONFIG_PROFILE_PRIORITY_QUEUE_LIST.";
        }
        leaf min-green {
          type omci-types:omci-uint16;
          description
            "min green";
        }
        leaf max-green {
          type omci-types:omci-uint16;
          description
            "max green";
        }
        leaf min-yellow {
          type omci-types:omci-uint16;
          description
            "min yellow";
        }
        leaf max-yellow {
          type omci-types:omci-uint16;
          description
            "max yellow";
        }
      }
    }
    container PON_SERVICE_CONFIG_PROFILE_RS232_RS485_PERF_MON_HIST_DATA {
      description
        "RS232/RS485 performance monitoring history data, Class Value 403. This ME collects PM data for a RS232/RS485 interface. Instances of this ME are created and deleted by the OLT. ConfigDB table: PON_SERVICE_CONFIG_PROFILE_RS232_RS485_PERF_MON_HIST_DATA.";
      reference
        "G.988, 9.15.3, RS232/RS485 performance monitoring history data";
      list PON_SERVICE_CONFIG_PROFILE_RS232_RS485_PERF_MON_HIST_DATA_LIST {
        key "service-config-profile-name managed-entity-id";
        description
          "PON_SERVICE_CONFIG_PROFILE_OMCI_CLASS_RS232_RS485_PERF_MON_HIST_DATA_MANAGED_ENTITY configuration.
           ConfigDB key: PON_SERVICE_CONFIG_PROFILE_RS232_RS485_PERF_MON_HIST_DATA|<service-config-profile-name>|<managed-entity-id>.";
        leaf service-config-profile-name {
          type string;
        }
        leaf managed-entity-id {
          type omci-types:omci-uint16;
          description
            "Managed entity ID: This attribute uniquely identifies each instance of this ME. Through an identical ID, this ME is implicitly linked to an instance of the PPTP RS232/RS485 UNI. (R, set-by-create) (mandatory) (2bytes)";
        }
        leaf threshold-data-1-2-id {
          type omci-types:omci-uint16;
          description
            "Threshold data 1/2 id: This attribute points to an instance of the threshold data 1 and 2 MEs that contains PM threshold values. (R,W, set-by-create) (mandatory) (2bytes)";
        }
      }
    }
    container PON_SERVICE_CONFIG_PROFILE_RS232_RS485_PORT_OPER_CONFIG_DATA {
      description
        "RS232/RS485 port operation configuration data, Class Value 402. This ME specifies the RS232/RS485 port operation mode. The ONU automatically creates instances of this ME if RS232/RS485 data acquisition services are available. ConfigDB table: PON_SERVICE_CONFIG_PROFILE_RS232_RS485_PORT_OPER_CONFIG_DATA.";
      reference
        "G.988, 9.15.2, RS232/RS485 port operation configuration data";
      list PON_SERVICE_CONFIG_PROFILE_RS232_RS485_PORT_OPER_CONFIG_DATA_LIST {
        key "service-config-profile-name managed-entity-id";
        description
          "PON_SERVICE_CONFIG_PROFILE_OMCI_CLASS_RS232_RS485_PORT_OPER_CONFIG_DATA_MANAGED_ENTITY configuration.
           ConfigDB key: PON_SERVICE_CONFIG_PROFILE_RS232_RS485_PORT_OPER_CONFIG_DATA|<service-config-profile-name>|<managed-entity-id>.";
        leaf service-config-profile-name {
          type string;
        }
        leaf managed-entity-id {
          type omci-types:omci-uint16;
          description
            "Managed entity ID: This attribute uniquely identifies each instance of this ME. (R, set-by-create) (mandatory) (2bytes)";
        }
        leaf tcp-udp-ptr {
          type omci-types:omci-uint16;
          description
            "TCP/UDP pointer: This pointer associates the RS232/RS485 port operation configuration with the TCP/UDP config data ME to be used for communication with the serial server. The default value is 0xFFFF, a null pointer. (R,W) (mandatory) (2bytes)";
        }
        leaf pptp-ptr {
          type omci-types:omci-uint16;
          description
            "PPTP pointer: This attribute points to the PPTP RS232/RS485 UNI ME that serves the serial data acquisition function. (R,W, set-by-create) (mandatory) (2bytes)";
        }
      }
    }
    container PON_SERVICE_CONFIG_PROFILE_SSH_SERVER_OPERATION {
      description
        "Ssh Server Operation, Class Value 251. ConfigDB table: PON_SERVICE_CONFIG_PROFILE_SSH_SERVER_OPERATION.";
      reference
        "G.988, Vendor specific";
      list PON_SERVICE_CONFIG_PROFILE_SSH_SERVER_OPERATION_LIST {
        key "service-config-profile-name managed-entity-id";
        description
          "PON_SERVICE_CONFIG_PROFILE_OMCI_CLASS_SSH_SERVER_OPERATION_MANAGED_ENTITY configuration.
           ConfigDB key: PON_SERVICE_CONFIG_PROFILE_SSH_SERVER_OPERATION|<service-config-profile-name>|<managed-entity-id>.";
        leaf service-config-profile-name {
          type string;
        }
        leaf managed-entity-id {
          type omci-types:omci-uint16;
          description
            "Managed Entity Id";
        }
        leaf server-action {
          type omci-types:omci-uint8;
          description
            "Server Action";
        }
      }
    }
    container PON_SERVICE_CONFIG_PROFILE_SSH_SERVER_PORT_DATA {
      description
        "Ssh Server Port Data, Class Value 252. ConfigDB table: PON_SERVICE_CONFIG_PROFILE_SSH_SERVER_PORT_DATA.";
      reference
        "G.988, Vendor specific";
      list PON_SERVICE_CONFIG_PROFILE_SSH_SERVER_PORT_DATA_LIST {
        key "service-config-profile-name managed-entity-id";
        description
          "PON_SERVICE_CONFIG_PROFILE_OMCI_CLASS_SSH_SERVER_PORT_DATA_MANAGED_ENTITY configuration.
           ConfigDB key: PON_SERVICE_CONFIG_PROFILE_SSH_SERVER_PORT_DATA|<service-config-profile-name>|<managed-entity-id>.";
        leaf service-config-profile-name {
          type string;
        }
        leaf managed-entity-id {
          type omci-types:omci-uint16;
          description
            "Managed Entity Id";
        }
        leaf tcp-udp-ptr {
          type omci-types:omci-uint16;
          description
            "Tcp Udp Ptr";
        }
        leaf ssh-server-ptr {
          type omci-types:omci-uint16;
          description
            "Ssh Server Ptr";
        }
      }
    }
    container PON_SERVICE_CONFIG_PROFILE_TCONT {
      description
        "T-CONT, Class Value 262. This ME represents a logical traffic container associated with a PON alloc-ID. ConfigDB table: PON_SERVICE_CONFIG_PROFILE_TCONT.";
      reference
        "G.988, 9.2.2, T-CONT";
      list PON_SERVICE_CONFIG_PROFILE_TCONT_LIST {
        key "service-config-profile-name managed-entity-id";
        description
          "PON_SERVICE_CONFIG_PROFILE_OMCI_CLASS_TCONT_MANAGED_ENTITY configuration.
           ConfigDB key: PON_SERVICE_CONFIG_PROFILE_TCONT|<service-config-profile-name>|<managed-entity-id>.";
        leaf service-config-profile-name {
          type string;
        }
        leaf managed-entity-id {
          type omci-types:omci-uint16;
          description
            "Managed entity ID: This attribute uniquely identifies each instance of this ME. This 2byte number indicates the physical capability that realizes the T-CONT. It may be represented as 0xSSBB, where SS indicates the slot ID that contains this T-CONT (0 for the ONU as a whole), and BB is the T-CONT ID, numbered by the ONU itself. T-CONTs are numbered in ascending order, with the range 0..255 in each slot. (R) (mandatory) (2bytes)";
        }
        leaf alloc-id {
          type omci-types:omci-uint16;
          description
            "Alloc-ID: This attribute links the T-CONT with the alloc-ID assigned by the OLT in the assign_alloc-ID PLOAM message. The respective TC layer specification should be referenced for the legal values for that system. Prior to the setting of this attribute by the OLT, this attribute has an unambiguously unusable initial value, namely the value 0x00FF or 0xFFFF for ITU-T G.984 systems, and the value 0xFFFF for all other ITU-T GTC based PON systems. (R,W) (mandatory) (2bytes)";
        }
        leaf policy {
          type omci-types:omci-uint8;
          description
            "Policy: This attribute indicates the T-CONT's traffic scheduling policy. Valid values: 0 Null 1 Strict priority 2 WRR Weighted round robin (R, W) (mandatory) (1 byte) NOTE This attribute is read-only, unless otherwise specified by the QoS configuration flexibility attribute of the ONU2-G ME. If flexible configuration is not supported, the ONU should reject an attempt to set it with a parameter error result-reason code.";
        }
      }
    }
    container PON_SERVICE_CONFIG_PROFILE_TCP_UDP_CONFIG_DATA {
      description
        "TCP/UDP config data, Class Value 136. This ME configures TCP/UDP services exposed from an IP host context. ConfigDB table: PON_SERVICE_CONFIG_PROFILE_TCP_UDP_CONFIG_DATA.";
      reference
        "G.988, 9.4.3, TCP/UDP config data";
      list PON_SERVICE_CONFIG_PROFILE_TCP_UDP_CONFIG_DATA_LIST {
        key "service-config-profile-name managed-entity-id";
        description
          "PON_SERVICE_CONFIG_PROFILE_OMCI_CLASS_TCP_UDP_CONFIG_DATA_MANAGED_ENTITY configuration.
           ConfigDB key: PON_SERVICE_CONFIG_PROFILE_TCP_UDP_CONFIG_DATA|<service-config-profile-name>|<managed-entity-id>.";
        leaf service-config-profile-name {
          type string;
        }
        leaf managed-entity-id {
          type omci-types:omci-uint16;
          description
            "Managed entity ID: This attribute uniquely identifies each instance of this ME. It is recommended that the ME ID be the same as the port number. (R, set-by- create) (mandatory) (2bytes)";
        }
        leaf port-id {
          type omci-types:omci-uint16;
          description
            "Port ID: This attribute specifies the port number that offers the TCP/UDP service. (R,W, set-by-create) (mandatory) (2bytes)";
        }
        leaf protocol {
          type omci-types:omci-uint8;
          description
            "Protocol: This attribute specifies the protocol type as defined by [b-IANA] (protocol numbers), for example UDP (0x11). (R,W, set-by-create) (mandatory) (1byte)";
        }
        leaf tos-diffserv-field {
          type omci-types:omci-uint8;
          description
            "TOS/diffserv field: This attribute specifies the value of the TOS/diffserv field of the IPv4 header. The contents of this attribute may contain the type of service per [IETF RFC 2474] or a DSCP. Valid values for DSCP are as defined by [b-IANA] (differentiated services field code points). (R,W, set-by-create) (mandatory) (1byte)";
        }
        leaf ip-host-ptr {
          type omci-types:omci-uint16;
          description
            "IP host pointer: This attribute points to the IP host config data or IPv6 host config data ME associated with this TCP/UDP data. Any number of ports and protocols may be associated with an IP host. (R, W, set-by-create) (mandatory) (2 bytes)";
        }
      }
    }
    container PON_SERVICE_CONFIG_PROFILE_TCP_UDP_PERF_MON_HIST_DATA {
      description
        "TCP/UDP performance monitoring history data, Class Value 342. This ME collects PM data related to a TCP or UDP port. Instances of this ME are created and deleted by the OLT. For a complete discussion of generic PM architecture, refer to clause I.4. ConfigDB table: PON_SERVICE_CONFIG_PROFILE_TCP_UDP_PERF_MON_HIST_DATA.";
      reference
        "G.988, 9.4.4, TCP/UDP performance monitoring history data";
      list PON_SERVICE_CONFIG_PROFILE_TCP_UDP_PERF_MON_HIST_DATA_LIST {
        key "service-config-profile-name managed-entity-id";
        description
          "PON_SERVICE_CONFIG_PROFILE_OMCI_CLASS_TCP_UDP_PERF_MON_HIST_DATA_MANAGED_ENTITY configuration.
           ConfigDB key: PON_SERVICE_CONFIG_PROFILE_TCP_UDP_PERF_MON_HIST_DATA|<service-config-profile-name>|<managed-entity-id>.";
        leaf service-config-profile-name {
          type string;
        }
        leaf managed-entity-id {
          type omci-types:omci-uint16;
          description
            "Managed entity ID: This attribute uniquely identifies each instance of this ME. Through an identical ID, this ME is implicitly linked to an instance of the TCP/UDP config data ME. (R, set-by-create) (mandatory) (2bytes)";
        }
        leaf threshold-data-1-2-id {
          type omci-types:omci-uint16;
          description
            "Threshold data 1/2 ID: This attribute points to an instance of the threshold data 1 ME that contains PM threshold values. Since no threshold value attribute number exceeds 7, a threshold data 2 ME is optional. (R,W, set-by-create) (mandatory) (2bytes)";
        }
      }
    }
    container PON_SERVICE_CONFIG_PROFILE_THRESHOLD_DATA64_BIT {
      description
        "Threshold Data64 Bit, Class Value 426. ConfigDB table: PON_SERVICE_CONFIG_PROFILE_THRESHOLD_DATA64_BIT.";
      reference
        "G.988, Threshold Data64 Bit";
      list PON_SERVICE_CONFIG_PROFILE_THRESHOLD_DATA64_BIT_LIST {
        key "service-config-profile-name managed-entity-id";
        description
          "PON_SERVICE_CONFIG_PROFILE_OMCI_CLASS_THRESHOLD_DATA64_BIT_MANAGED_ENTITY configuration.
           ConfigDB key: PON_SERVICE_CONFIG_PROFILE_THRESHOLD_DATA64_BIT|<service-config-profile-name>|<managed-entity-id>.";
        leaf service-config-profile-name {
          type string;
        }
        leaf managed-entity-id {
          type omci-types:omci-uint16;
          description
            "Managed Entity Id";
        }
        leaf threshold-value-1 {
          type omci-types:omci-uint64;
          description
            "Threshold Value 1";
        }
        leaf threshold-value-2 {
          type omci-types:omci-uint64;
          description
            "Threshold Value 2";
        }
        leaf threshold-value-3 {
          type omci-types:omci-uint64;
          description
            "Threshold Value 3";
        }
        leaf threshold-value-4 {
          type omci-types:omci-uint64;
          description
            "Threshold Value 4";
        }
        leaf threshold-value-5 {
          type omci-types:omci-uint64;
          description
            "Threshold Value 5";
        }
        leaf threshold-value-6 {
          type omci-types:omci-uint64;
          description
            "Threshold Value 6";
        }
        leaf threshold-value-7 {
          type omci-types:omci-uint64;
          description
            "Threshold Value 7";
        }
        leaf threshold-value-8 {
          type omci-types:omci-uint64;
          description
            "Threshold Value 8";
        }
        leaf threshold-value-9 {
          type omci-types:omci-uint64;
          description
            "Threshold Value 9";
        }
        leaf threshold-value-10 {
          type omci-types:omci-uint64;
          description
            "Threshold Value 10";
        }
        leaf threshold-value-11 {
          type omci-types:omci-uint64;
          description
            "Threshold Value 11";
        }
        leaf threshold-value-12 {
          type omci-types:omci-uint64;
          description
            "Threshold Value 12";
        }
        leaf threshold-value-13 {
          type omci-types:omci-uint64;
          description
            "Threshold Value 13";
        }
        leaf threshold-value-14 {
          type omci-types:omci-uint64;
          description
            "Threshold Value 14";
        }
      }
    }
    container PON_SERVICE_CONFIG_PROFILE_THRESHOLD_DATA_ONE {
      description
        "Threshold data 1, Class Value 273. Threshold data are partitioned into two MEs for historical reasons. An instance of this ME, together with an optional instance of the threshold data 2 ME, contains threshold values for counters in PM history data MEs. For a complete discussion of generic PM architecture, refer to clause I.4. Instances of this ME are created and deleted by the OLT. ConfigDB table: PON_SERVICE_CONFIG_PROFILE_THRESHOLD_DATA_ONE.";
      reference
        "G.988, 9.12.6, Threshold data 1";
      list PON_SERVICE_CONFIG_PROFILE_THRESHOLD_DATA_ONE_LIST {
        key "service-config-profile-name managed-entity-id";
        description
          "PON_SERVICE_CONFIG_PROFILE_OMCI_CLASS_THRESHOLD_DATA_ONE_MANAGED_ENTITY configuration.
           ConfigDB key: PON_SERVICE_CONFIG_PROFILE_THRESHOLD_DATA_ONE|<service-config-profile-name>|<managed-entity-id>.";
        leaf service-config-profile-name {
          type string;
        }
        leaf managed-entity-id {
          type omci-types:omci-uint16;
          description
            "Managed entity ID: This attribute uniquely identifies each instance of this ME. (R, set-by-create) (mandatory) (2bytes) The following seven attributes specify threshold values for seven thresholded counters in associated PM history data MEs. The definition of each PM history ME includes a table that links each thresholded counter to one of these threshold value attributes.";
        }
        leaf threshold-value-1 {
          type omci-types:omci-uint32;
          description
            "Threshold value1: (R,W, set-by-create) (mandatory) (4bytes)";
        }
        leaf threshold-value-2 {
          type omci-types:omci-uint32;
          description
            "Threshold value2: (R,W, set-by-create) (mandatory) (4bytes)";
        }
        leaf threshold-value-3 {
          type omci-types:omci-uint32;
          description
            "Threshold value3: (R,W, set-by-create) (mandatory) (4bytes)";
        }
        leaf threshold-value-4 {
          type omci-types:omci-uint32;
          description
            "Threshold value4: (R,W, set-by-create) (mandatory) (4bytes)";
        }
        leaf threshold-value-5 {
          type omci-types:omci-uint32;
          description
            "Threshold value5: (R,W, set-by-create) (mandatory) (4bytes)";
        }
        leaf threshold-value-6 {
          type omci-types:omci-uint32;
          description
            "Threshold value6: (R,W, set-by-create) (mandatory) (4bytes)";
        }
        leaf threshold-value-7 {
          type omci-types:omci-uint32;
          description
            "Threshold value7: (R,W, set-by-create) (mandatory) (4bytes)";
        }
      }
    }
    container PON_SERVICE_CONFIG_PROFILE_THRESHOLD_DATA_TWO {
      description
        "Threshold data 2, Class Value 274. Together with an instance of the threshold data 1 ME, an instance of this ME contains threshold values for counters maintained in one or more instances of PM history data MEs. For a complete discussion of generic PM architecture, refer to clauseI.4. Instances of this ME are created and deleted by the OLT. ConfigDB table: PON_SERVICE_CONFIG_PROFILE_THRESHOLD_DATA_TWO.";
      reference
        "G.988, 9.12.7, Threshold data 2";
      list PON_SERVICE_CONFIG_PROFILE_THRESHOLD_DATA_TWO_LIST {
        key "service-config-profile-name managed-entity-id";
        description
          "PON_SERVICE_CONFIG_PROFILE_OMCI_CLASS_THRESHOLD_DATA_TWO_MANAGED_ENTITY configuration.
           ConfigDB key: PON_SERVICE_CONFIG_PROFILE_THRESHOLD_DATA_TWO|<service-config-profile-name>|<managed-entity-id>.";
        leaf service-config-profile-name {
          type string;
        }
        leaf managed-entity-id {
          type omci-types:omci-uint16;
          description
            "Managed entity ID: This attribute uniquely identifies each instance of this ME. Its value is the same as that of the paired threshold data1instance. (R, set- by-create) (mandatory) (2bytes) The following seven attributes specify threshold values for seven thresholded counters in associated PM history data MEs. The definition of each PM history ME includes a table that links each thresholded counter to one of these threshold value attributes.";
        }
        leaf threshold-value-8 {
          type omci-types:omci-uint32;
          description
            "Threshold value8: (R,W, set-by-create) (mandatory) (4bytes)";
        }
        leaf threshold-value-9 {
          type omci-types:omci-uint32;
          description
            "Threshold value9: (R,W, set-by-create) (mandatory) (4bytes)";
        }
        leaf threshold-value-10 {
          type omci-types:omci-uint32;
          description
            "Threshold value10: (R,W, set-by-create) (mandatory) (4bytes)";
        }
        leaf threshold-value-11 {
          type omci-types:omci-uint32;
          description
            "Threshold value11: (R,W, set-by-create) (mandatory) (4bytes)";
        }
        leaf threshold-value-12 {
          type omci-types:omci-uint32;
          description
            "Threshold value12: (R,W, set-by-create) (mandatory) (4bytes)";
        }
        leaf threshold-value-13 {
          type omci-types:omci-uint32;
          description
            "Threshold value13: (R,W, set-by-create) (mandatory) (4bytes)";
        }
        leaf threshold-value-14 {
          type omci-types:omci-uint32;
          description
            "Threshold value14: (R,W, set-by-create) (mandatory) (4bytes)";
        }
      }
    }
    container PON_SERVICE_CONFIG_PROFILE_TRAFFIC_DESCRIPTOR {
      description
        "Traffic descriptor, Class Value 280. The traffic descriptor is a profile that allows for traffic management. A priority controlled ONU can point from a MAC bridge port configuration data ME to a traffic descriptor in order to implement traffic management (marking, policing). A rate controlled ONU can point to a traffic descriptor from either a MAC bridge port configuration data ME or a GEM port network CTP to implement traffic management (marking, shaping). Packets are determined to be green, yellow or red as a function of the ingress packet rate and the settings in this ME. The colour indicates drop precedence (eligibility), subsequently used by the priority queue ME to drop packets conditionally during congestion conditions. Packet colour is also used by the optional mode 1 DBA status reporting function described in [ITU-T G.984.3]. Red packets are dropped immediately. Yellow packets are marked as drop eligible, and green packets are marked as not drop eligible, according to the egress colour marking attribute. The algorithm used to determine the colour marking is specified by the meter type attribute. If [b-IETF RFC 4115] is used, then: CIR4115=CIR EIR4115=PIR CIR (EIR: excess information rate) CBS4115=CBS EBS4115=PBS CBS. ConfigDB table: PON_SERVICE_CONFIG_PROFILE_TRAFFIC_DESCRIPTOR.";
      reference
        "G.988, 9.2.12, Traffic descriptor";
      list PON_SERVICE_CONFIG_PROFILE_TRAFFIC_DESCRIPTOR_LIST {
        key "service-config-profile-name managed-entity-id";
        description
          "PON_SERVICE_CONFIG_PROFILE_OMCI_CLASS_TRAFFIC_DESCRIPTOR_MANAGED_ENTITY configuration.
           ConfigDB key: PON_SERVICE_CONFIG_PROFILE_TRAFFIC_DESCRIPTOR|<service-config-profile-name>|<managed-entity-id>.";
        leaf service-config-profile-name {
          type string;
        }
        leaf managed-entity-id {
          type omci-types:omci-uint16;
          description
            "Managed entity ID: This attribute uniquely identifies each instance of this ME. (R, set-by-create) (mandatory) (2bytes)";
        }
        leaf cir {
          type omci-types:omci-uint32;
          description
            "CIR: This attribute specifies the committed information rate, in bytes per second. The default is 0. (R,W, set-by-create) (optional) (4bytes)";
        }
        leaf pir {
          type omci-types:omci-uint32;
          description
            "PIR: This attribute specifies the peak information rate, in bytes per second. The default value 0 accepts the ONU's factory policy. (R,W, set-by-create) (optional) (4bytes)";
        }
        leaf cbs {
          type omci-types:omci-uint32;
          description
            "CBS: This attribute specifies the committed burst size, in bytes. The default is 0. (R,W, set-by-create) (optional) (4bytes)";
        }
        leaf pbs {
          type omci-types:omci-uint32;
          description
            "PBS: This attribute specifies the peak burst size, in bytes. The default value 0 accepts the ONU's factory policy. (R,W, set-by-create) (optional) (4bytes)";
        }
        leaf colour-mode {
          type omci-types:omci-uint8;
          description
            "Colour mode: This attribute specifies whether the colour marking algorithm considers pre-existing marking on ingress packets (colour-aware) or ignores it (colour-blind). In colour-aware mode, packets can only be demoted (from green to yellow or red, or from yellow to red). The default value is 0. 0 Colour-blind 1 Colour-aware (R,W, set-by-create) (optional) (1byte)";
        }
        leaf ingress-colour-marking {
          type omci-types:omci-uint8;
        }
        leaf egress-colour-marking {
          type omci-types:omci-uint8;
        }
      }
    }
    container PON_SERVICE_CONFIG_PROFILE_TRAFFIC_SCHEDULER {
      description
        "Traffic scheduler, Class Value 278. This ME models a logical scheduler that controls upstream GEM packet scheduling chains. ConfigDB table: PON_SERVICE_CONFIG_PROFILE_TRAFFIC_SCHEDULER.";
      reference
        "G.988, 9.2.11, Traffic scheduler";
      list PON_SERVICE_CONFIG_PROFILE_TRAFFIC_SCHEDULER_LIST {
        key "service-config-profile-name managed-entity-id";
        description
          "PON_SERVICE_CONFIG_PROFILE_OMCI_CLASS_TRAFFIC_SCHEDULER_MANAGED_ENTITY configuration.
           ConfigDB key: PON_SERVICE_CONFIG_PROFILE_TRAFFIC_SCHEDULER|<service-config-profile-name>|<managed-entity-id>.";
        leaf service-config-profile-name {
          type string;
        }
        leaf managed-entity-id {
          type omci-types:omci-uint16;
          description
            "Managed entity ID: This attribute uniquely identifies each instance of this ME. This 2byte number indicates the physical capability that realizes the traffic scheduler. The first byte is the slot ID of the circuit pack with which this traffic scheduler is associated. For a traffic scheduler that is not associated with a circuit pack, the first byte is 0xFF. The second byte is the traffic scheduler id, assigned by the ONU itself. Traffic schedulers are numbered in ascending order with the range 0..0xFF in each circuit pack or in the ONU core. (R) (mandatory) (2bytes)";
        }
        leaf tcont-pointer {
          type omci-types:omci-uint16;
          description
            "T-CONT pointer: This attribute points to a T-CONT instance. (R,W, set-by- create) (mandatory) (2bytes)";
        }
        leaf policy {
          type omci-types:omci-uint8;
          description
            "Policy: This attribute represents scheduling policy. Valid values include: 0 Null 1 Strict priority 2 WRR (weighted round robin) The traffic scheduler derives priority or weight values for its tributary traffic schedulers or priority queues from the tributary MEs themselves. (R, W) (mandatory) (1 byte) NOTE 3 This attribute is read-only unless otherwise specified by the QoS configuration flexibility attribute of the ONU2-G ME. If flexible configuration is not supported, the ONU should reject an attempt to set the policy attribute with a parameter error result-reason code.";
        }
        leaf priority-weight {
          type omci-types:omci-uint8;
          description
            "Priority/weight: This attribute represents the priority for strict priority scheduling or the weight for WRR scheduling. This value is used by the next upstream ME, as indicated by the T-CONT pointer attribute or traffic scheduler pointer attribute. If the indicated pointer has policy=strict priority, this value is interpreted as a priority (0 is the highest priority, 255 the lowest). If the indicated pointer has policy=WRR, this value is interpreted as a weight. Higher values receive more bandwidth. Upon ME instantiation, the ONU sets this attribute to 0. (R,W) (mandatory) (1byte)";
        }
      }
    }
    container PON_SERVICE_CONFIG_PROFILE_VIRTUAL_ETHERNET_INTERFACE_PT {
      description
        "Virtual Ethernet interface point, Class Value 329. This ME represents the data plane hand-off point in an ONU to a separate (non- OMCI) management domain. The VEIP is managed by the OMCI, and is potentially known to the non-OMCI management domain. One or more Ethernet traffic flows are present at this boundary. Instances of this ME are automatically created and deleted by the ONU. This is necessary because the required downstream priority queues are subject to physical implementation constraints. The OLT may use one or more of the VEIPs created by the ONU. It is expected that the ONU will create one VEIP for each non-OMCI management domain. At the vendor's discretion, a VEIP may be created for each traffic class. ConfigDB table: PON_SERVICE_CONFIG_PROFILE_VIRTUAL_ETHERNET_INTERFACE_PT.";
      reference
        "G.988, 9.5.5, Virtual Ethernet interface point";
      list PON_SERVICE_CONFIG_PROFILE_VIRTUAL_ETHERNET_INTERFACE_PT_LIST {
        key "service-config-profile-name managed-entity-id";
        description
          "PON_SERVICE_CONFIG_PROFILE_OMCI_CLASS_VIRTUAL_ETHERNET_INTERFACE_PT_MANAGED_ENTITY configuration.
           ConfigDB key: PON_SERVICE_CONFIG_PROFILE_VIRTUAL_ETHERNET_INTERFACE_PT|<service-config-profile-name>|<managed-entity-id>.";
        leaf service-config-profile-name {
          type string;
        }
        leaf managed-entity-id {
          type omci-types:omci-uint16;
          description
            "Managed entity ID: This attribute uniquely identifies each instance of this ME. When used independently of a cardholder and circuit pack, the ONU should assign IDs in the sequence 1, 2, .... When used in conjunction with a cardholder and circuit pack, this 2 byte number indicates the physical position of the VEIP. The first byte is the slot ID (defined in clause 9.1.5). The second byte is the port ID, with the range 1..255. The values 0 and 0xFFFF are reserved. (R) (mandatory) (2 bytes)";
        }
        leaf administrative-state {
          type omci-types:omci-uint8;
          description
            "Administrative state: This attribute locks (1) and unlocks (0) the functions performed by this ME. Administrative state is further described in clause A.1.6. (R,W) (mandatory) (1byte)";
        }
        leaf interdomain-service-config-profile-name {
          type omci-types:omci-string;
        }
        leaf tcp-udp-pointer {
          type omci-types:omci-uint16;
          description
            "TCP/UDP pointer: This attribute points to an instance of the TCP/UDP config data ME, which provides for OMCI management of the non-OMCI management domain's IP connectivity. If no OMCI management of the non-OMCI domain's IP connectivity is required, this attribute may be omitted or set to its default, a null pointer. (R,W) (optional) (2bytes)";
        }
      }
    }
    container PON_SERVICE_CONFIG_PROFILE_VLAN_TAGGING_FILTER_DATA {
      description
        "VLAN tagging filter data, Class Value 84. This ME organizes data associated with VLAN tagging. Instances of this ME are created and deleted by the OLT. ConfigDB table: PON_SERVICE_CONFIG_PROFILE_VLAN_TAGGING_FILTER_DATA.";
      reference
        "G.988, 9.3.11, VLAN tagging filter data";
      list PON_SERVICE_CONFIG_PROFILE_VLAN_TAGGING_FILTER_DATA_LIST {
        key "service-config-profile-name managed-entity-id";
        description
          "PON_SERVICE_CONFIG_PROFILE_OMCI_CLASS_VLAN_TAGGING_FILTER_DATA_MANAGED_ENTITY configuration.
           ConfigDB key: PON_SERVICE_CONFIG_PROFILE_VLAN_TAGGING_FILTER_DATA|<service-config-profile-name>|<managed-entity-id>.";
        leaf service-config-profile-name {
          type string;
        }
        leaf managed-entity-id {
          type omci-types:omci-uint16;
          description
            "Managed entity ID: This attribute uniquely identifies each instance of this ME. Through an identical ID, this ME is implicitly linked to an instance of the MAC bridge port configuration data ME. (R, set-by-create) (mandatory) (2bytes)";
        }
        leaf forward-operation {
          type omci-types:omci-uint8;
          description
            "Forward operation: When a frame passes through the MAC bridge port, it is processed according to the operation specified by this attribute, in accordance with Table9.3.11-1. Figure 9.3.11-3 illustrates the treatment of frames according to the provisioned action possibilities. Tagged and untagged frames are treated separately, but both in accordance with Figure 9.3.11-3. While all forwarding operations are plausible, only actions 0x10 and 0x12 are necessary to construct a VLAN mapper and an 802.1p mapper, respectively. (R,W, set-by- create) (mandatory) (1byte) Table 9.3.11-1 contains duplicate entries due to simplification of the original set of actions. Table 9.3.11-1 and the actions listed are discussed in detail in the following.";
        }
        leaf number-of-entries {
          type omci-types:omci-uint8;
          description
            "Number of entries: This attribute specifies the number of valid entries in the VLAN filter list. (R,W, set-by-create) (mandatory) (1byte)";
        }
      }
    }
    container PON_SERVICE_CONFIG_PROFILE_VLAN_TAGGING_FILTER_DATA_VLAN_FILTER {
      description
        "VLAN filter list entry for VLAN tagging filter data. Each entry contains a VLAN filter TCI value. ConfigDB table: PON_SERVICE_CONFIG_PROFILE_VLAN_TAGGING_FILTER_DATA_VLAN_FILTER.";
      list PON_SERVICE_CONFIG_PROFILE_VLAN_TAGGING_FILTER_DATA_VLAN_FILTER_LIST {
        key "service-config-profile-name id managed-entity-id vlan-filter-entry-id";
        description
          "PON_SERVICE_CONFIG_PROFILE_OMCI_CLASS_VLAN_TAGGING_FILTER_DATA_MANAGED_ENTITY_VLAN_FILTER configuration.
           ConfigDB key: PON_SERVICE_CONFIG_PROFILE_VLAN_TAGGING_FILTER_DATA_VLAN_FILTER|<service-config-profile-name>|<id>|<managed-entity-id>|<vlan-filter-entry-id>.";
        leaf service-config-profile-name {
          type string;
        }
        leaf id {
          type string;
          description
            "Table entry number starting at '0'";
        }
        leaf managed-entity-id {
          type omci-types:omci-uint16;
          description
            "Managed entity ID: This attribute uniquely identifies each instance of this ME. Through an identical ID, this ME is implicitly linked to an instance of the MAC bridge port configuration data ME. (R, set-by-create) (mandatory) (2bytes)";
        }
        leaf vlan-filter-entry-id {
          type uint8;
        }
        leaf vlan-id {
          type omci-types:omci-uint16;
          description
            "VLAN ID";
        }
      }
    }
    container PON_SERVICE_CONFIG_PROFILE_XG_PON_DOWNSTREAM_MGMT_PERF_MON_HIST_DATA {
      description
        "XG-PON downstream management performance monitoring history data, Class Value 345. This ME collects PM data associated with the XG-PON TC layer. It collects counters associated with downstream PLOAM and OMCI messages. For a complete discussion of generic PM architecture, refer to clause I.4. ConfigDB table: PON_SERVICE_CONFIG_PROFILE_XG_PON_DOWNSTREAM_MGMT_PERF_MON_HIST_DATA.";
      reference
        "G.988, 9.2.16, XG-PON downstream management performance monitoring history data";
      list PON_SERVICE_CONFIG_PROFILE_XG_PON_DOWNSTREAM_MGMT_PERF_MON_HIST_DATA_LIST {
        key "service-config-profile-name managed-entity-id";
        description
          "PON_SERVICE_CONFIG_PROFILE_OMCI_CLASS_XG_PON_DOWNSTREAM_MGMT_PERF_MON_HIST_DATA_MANAGED_ENTITY configuration.
           ConfigDB key: PON_SERVICE_CONFIG_PROFILE_XG_PON_DOWNSTREAM_MGMT_PERF_MON_HIST_DATA|<service-config-profile-name>|<managed-entity-id>.";
        leaf service-config-profile-name {
          type string;
        }
        leaf managed-entity-id {
          type omci-types:omci-uint16;
          description
            "Managed entity ID: This attribute uniquely identifies each instance of this ME. Through an identical ID, this ME is implicitly linked to an instance of the ANI-G. (R, set-by-create) (mandatory) (2bytes)";
        }
        leaf threshold-data-1-2-id {
          type omci-types:omci-uint16;
          description
            "Threshold data 1/2 ID: This attribute points to an instance of the threshold data 1 ME that contains PM threshold values. Since no threshold value attribute number exceeds 7, a threshold data 2 ME is optional. (R,W, set-by-create) (mandatory) (2bytes)";
        }
      }
    }
    container PON_SERVICE_CONFIG_PROFILE_XG_PON_TC_PERF_MON_HIST_DATA {
      description
        "XG-PON TC performance monitoring history data, Class Value 344. This ME collects PM data associated with the XG-PON TC layer. For a complete discussion of generic PM architecture, refer to clause I.4. ConfigDB table: PON_SERVICE_CONFIG_PROFILE_XG_PON_TC_PERF_MON_HIST_DATA.";
      reference
        "G.988, 9.2.15, XG-PON TC performance monitoring history data";
      list PON_SERVICE_CONFIG_PROFILE_XG_PON_TC_PERF_MON_HIST_DATA_LIST {
        key "service-config-profile-name managed-entity-id";
        description
          "PON_SERVICE_CONFIG_PROFILE_OMCI_CLASS_XG_PON_TC_PERF_MON_HIST_DATA_MANAGED_ENTITY configuration.
           ConfigDB key: PON_SERVICE_CONFIG_PROFILE_XG_PON_TC_PERF_MON_HIST_DATA|<service-config-profile-name>|<managed-entity-id>.";
        leaf service-config-profile-name {
          type string;
        }
        leaf managed-entity-id {
          type omci-types:omci-uint16;
          description
            "Managed entity ID: This attribute uniquely identifies each instance of this ME. Through an identical ID, this ME is implicitly linked to an instance of the ANI-G. (R, set-by-create) (mandatory) (2bytes)";
        }
        leaf threshold-data-1-2-id {
          type omci-types:omci-uint16;
          description
            "Threshold data 1/2 ID: This attribute points to an instance of the threshold data 1 ME that contains PM threshold values. (R,W, set-by-create) (mandatory) (2bytes)";
        }
      }
    }
    container PON_SERVICE_CONFIG_PROFILE_XG_PON_UPSTREAM_MGMT_PERF_MON_HIST_DATA {
      description
        "XG-PON upstream management performance monitoring history data, Class Value 346. This ME collects PM data associated with the XG-PON TC layer. It counts upstream PLOAM messages transmitted by the ONU. For a complete discussion of generic PM architecture, refer to clause I.4. ConfigDB table: PON_SERVICE_CONFIG_PROFILE_XG_PON_UPSTREAM_MGMT_PERF_MON_HIST_DATA.";
      reference
        "G.988, 9.2.17, XG-PON upstream management performance monitoring history data";
      list PON_SERVICE_CONFIG_PROFILE_XG_PON_UPSTREAM_MGMT_PERF_MON_HIST_DATA_LIST {
        key "service-config-profile-name managed-entity-id";
        description
          "PON_SERVICE_CONFIG_PROFILE_OMCI_CLASS_XG_PON_UPSTREAM_MGMT_PERF_MON_HIST_DATA_MANAGED_ENTITY configuration.
           ConfigDB key: PON_SERVICE_CONFIG_PROFILE_XG_PON_UPSTREAM_MGMT_PERF_MON_HIST_DATA|<service-config-profile-name>|<managed-entity-id>.";
        leaf service-config-profile-name {
          type string;
        }
        leaf managed-entity-id {
          type omci-types:omci-uint16;
          description
            "Managed entity ID: This attribute uniquely identifies each instance of this ME. Through an identical ID, this ME is implicitly linked to an instance of the ANI-G. (R, set-by-create) (mandatory) (2bytes)";
        }
        leaf threshold-data-1-2-id {
          type omci-types:omci-uint16;
          description
            "Threshold data 1/2 ID: No thresholds are defined for this ME. For uniformity with other PM, the attribute is retained and shown as mandatory, but it should be set to a null pointer. (R,W, set-by-create) (mandatory) (2bytes)";
        }
      }
    }
    container PON_SLA_PROFILE {
      description
        "PON_SLA_PROFILE table in ConfigDB.";
      list PON_SLA_PROFILE_LIST {
        key "sla-profile-name";
        description
          "List of SLA profiles.
           ConfigDB key: PON_SLA_PROFILE|<sla-profile-name>.";
        leaf sla-profile-name {
          description
            "Name identifier to reference this SLA profile.";
          type string {
            length "0..256";
          }
        }
        leaf downstream-guaranteed-rate {
          type uint32 {
            range "0..10000000 ";
          }
          units "kbps";
          default "128";
          description
            "Guaranteed (high priority) rate in kbps";
        }
        leaf downstream-guaranteed-maximum-burst {
          type uint32 {
            range "16000..1000000";
          }
          units "bytes";
          default "256000";
          description
            "Maximum burst size in Kilobytes. The guaranteed rate is enforced at this burst size.";
        }
        leaf downstream-best-effort-rate {
          type uint32 {
            range "0..10000000";
          }
          units "kbps";
          default "10000000";
          description
            "Best Effort (low priority) rate in kbps";
        }
        leaf downstream-best-effort-maximum-burst {
          type uint32 {
            range "16000..1000000";
          }
          units "bytes";
          default "256000";
          description
            "Maximum burst size in Kilobytes. The best effort rate is enforced at this burst size.";
        }
        leaf upstream-fixed-rate {
          type uint32 {
            range "0..8000000";
          }
          units "kbps";
          default "0";
          description
            "Fixed grant rate in kbps. This is an unsolicited grant by the DBA regardless of need.";
        }
        leaf upstream-guaranteed-rate {
          type uint32 {
            range "0..10000000";
          }
          units "kbps";
          default "128";
          description
            "Guaranteed (high priority) rate in kbps";
        }
        leaf upstream-guaranteed-maximum-burst {
          type uint32 {
            range "16000..1000000";
          }
          units "bytes";
          default "409600";
          description
            "Maximum burst size in Kilobytes. The guaranteed rate is enforced at this burst size.";
        }
        leaf upstream-priority {
          type uint8 {
            range "1..8";
          }
          default "1";
          description
            "Priority level for the guaranteed portion of the SLA.";
        }
        leaf upstream-best-effort-rate {
          type uint32 {
            range "0..10000000";
          }
          units "kbps";
          default "10000000";
          description
            "Best Effort (low priority) rate in kbps";
        }
        leaf upstream-best-effort-maximum-burst {
          type uint32 {
            range "16000..1000000";
          }
          units "bytes";
          default "409600";
          description
            "Maximum burst size in Kilobytes. The best effort rate is enforced at this burst size.";
        }
        leaf upstream-best-effort-priority {
          type uint8 {
            range "1..8";
          }
          default "1";
          description
            "Priority level for the Best Effort portion of the SLA.";
        }
      }
    }
    container PON_SLA_PROFILE_CONTROLLER {
      description
        "PON_SLA_PROFILE_CONTROLLER table in ConfigDB.";
      list PON_SLA_PROFILE_CONTROLLER_LIST {
        key "name";
        description
          "PON Controller related configuration.
           ConfigDB key: PON_SLA_PROFILE_CONTROLLER|<name>.";
        leaf name {
          type leafref {
            path "/sp:sonic-pon/sp:PON_SLA_PROFILE/sp:PON_SLA_PROFILE_LIST/sp:sla-profile-name";
          }
          description
            "References PON_SLA_PROFILE_LIST.";
        }
      }
    }
    container PON_OLT_PLUG {
      description
        "PON_OLT_PLUG table in ConfigDB.";
      list PON_OLT_PLUG_LIST {
        key "olt-name";
        description
          "PON OLT plug attributes regrouped from PON_OLT_INTF.
           ConfigDB key: PON_OLT_PLUG|<olt-name>.";
        leaf olt-name {
          type leafref {
            path "/sp:sonic-pon/sp:PON_OLT_INTF/sp:PON_OLT_INTF_LIST/sp:olt-intf-name";
          }
          description
            "References PON_OLT_INTF_LIST.";
        }
        leaf debug-log-level {
          type spt:logging-level;
          default "disable";
          description
            "Enables debug logging for this OLT plug.";
        }
        leaf fw-bank-ptr {
          type uint16 {
            range "0..3|65535";
          }
          default "65535";
          description
            "Firmware pointer to select bank (0 to 3) to be active on OLT plug. When this value changes, the OLT plug will be reset to load the firmware in the bank.";
        }
        leaf nni-max-frame-size {
          type uint32 {
            range "1518..12500";
          }
          default "9600";
          description
            "Maximum number of frame bytes from the DA to CRC32 for NNI receive path.
             (XGSPON-1518 to 9600)";
        }
      }
    }
    container PON_OLT_PROTECTION_GROUP {
      description
        "PON_OLT_PROTECTION_GROUP table in ConfigDB.";
      list PON_OLT_PROTECTION_GROUP_LIST {
        key "group-name";
        description
          "List of OLT PON protection groups.";
        leaf group-name {
          description
            "Name identifier used to reference this PON protection group.";
          type string {
            length "0..256";
          }
        }
        leaf admin-status {
          type boolean;
          default "true";
          description
            "Enables this PON protection group.";
        }
        leaf local-olt-interface {
          type leafref {
            path "/sp:sonic-pon/sp:PON_OLT_INTF/sp:PON_OLT_INTF_LIST/sp:olt-intf-name";
          }
          description
            "On-box (local) OLT interface member of this protection group.";
        }
        leaf peer-olt {
          description
            "Peer OLT hosting the peer protection interface. Omit for same-switch (local) protection.";
          type string {
            length "0..256";
          }
        }
        leaf peer-olt-interface {
          when "../coordination-mode = 'stateful'";
          description
            "References a peer OLT interface that that contains protection PON interface.";
          type string {
            length "0..256";
          }
        }
        leaf coordination-mode {
          description
            "PON protection coordination mode.";
          type enumeration {
            enum stateful {
              description
                "OLT-to-OLT coordination present";
            }
            enum stateless {
              description
                "No coordination; independent protection logic";
            }
          }
          default "stateful";
        }
        leaf revertive {
          type boolean;
          default "false";
          description
            "Auto revert when primary OLT interface recovers.";
        }
      }
    }
    container PON_CONTROLLER_STATE {
      description
        "PON_CONTROLLER_STATE table in StateDB.";
      config false;
      list PON_CONTROLLER_STATE_LIST {
        key "name";
        description
          "List of PON Controllers.
           StateDB key: PON_CONTROLLER_STATE|<name>.";
        leaf name {
          type string;
          description
            "Name identifier to reference this PON Controller.";
        }
        leaf timestamp {
          type yang:date-and-time;
          description
            "The last update for this state file";
        }
        leaf allow-unprovisioned-onus {
          type boolean;
          description
            "When false, the controller only allows ONUs that have been inventoried on an OLT
             to complete registration.";
        }
        leaf config-read-failed {
          type boolean;
          description
            "When true, the configuration file is not in a valid format and can't be
             read by the controller. All processing is stopped on this device until this
             error is fixed.
            ";
        }
        leaf interface {
          type string;
          description
            "Network interface used by the controller";
        }
        leaf olt-timeout {
          type uint32;
          description
            "The amount of time that the PON controller will lock an OLT for exclusive management.  When this timer expires, another PON controller can take control of the OLT.";
        }
        leaf statistics-sample {
          type uint32;
          units "seconds";
          description
            "Current statistic sample interval";
        }
        leaf version {
          type string;
          description
            "Version of the controller";
        }
        leaf unprovisioned-age {
          type uint32;
          units "seconds";
          description
            "The amount of time an ONU will be kept in the Unprovisioned ONUs
             list, when no longer attempting registration.";
        }
      }
    }
    container PON_CONTROLLER_ONU_FW_UPGRADE_STATE {
      description
        "PON_CONTROLLER_ONU_FW_UPGRADE_STATE table in StateDB.";
      config false;
      list PON_CONTROLLER_ONU_FW_UPGRADE_STATE_LIST {
        key "name onu-id";
        description
          "The list of ONUs currently performing firmware upgrades on the PON Controller.
           StateDB key: PON_CONTROLLER_ONU_FW_UPGRADE_STATE|<name>|<onu-id>.";
        leaf name {
          type string;
        }
        leaf onu-id {
          type string;
          description
            "ONU device identifier (XGS-PON: ONU Serial Number)";
        }
      }
    }
    container PON_CONTROLLER_SYSTEM_STATUS_OLT {
      description
        "PON_CONTROLLER_SYSTEM_STATUS_OLT table in StateDB.";
      config false;
      list PON_CONTROLLER_SYSTEM_STATUS_OLT_LIST {
        key "controller-name mac-address";
        description
          "The list of OLT plugs currently registered on this PON Controller.
           StateDB key: PON_CONTROLLER_SYSTEM_STATUS_OLT|<controller-name>|<mac-address>.";
        leaf controller-name {
          type string;
          description
            "References PON_CONTROLLER_SYSTEM_STATUS_LIST.";
        }
        leaf mac-address {
          type yang:mac-address;
          description
            "OLT plug MAC address.";
        }
        leaf olt-state {
          type string;
          description
            "The current state of the OLT plug.";
        }
        leaf onu-active-count {
          type uint32;
          description
            "The number of ONUs that are active on this OLT plug.";
        }
        leaf switch-chassis-id {
          type string;
          description
            "MAC address of switch.";
        }
        leaf switch-ipv4-address {
          type string;
          description
            "IP Address of the switch.";
        }
        leaf switch-ipv6-address {
          type string;
          description
            "IP Address of the switch.";
        }
        leaf switch-port-description {
          type string;
          description
            "String description of the port.";
        }
        leaf switch-port-id {
          type string;
          description
            "String identification for the port.";
        }
        leaf switch-system-description {
          type string;
          description
            "System Description.";
        }
        leaf switch-system-name {
          type string;
          description
            "Name for the Switch.";
        }
      }
    }
    container PON_CONTROLLER_SYSTEM_STATUS_OLT_ONU {
      description
        "PON_CONTROLLER_SYSTEM_STATUS_OLT_ONU table in StateDB.";
      config false;
      list PON_CONTROLLER_SYSTEM_STATUS_OLT_ONU_LIST {
        key "name mac-address onu-serial-number";
        description
          "The list of ONUs currently registered on this OLT.
           StateDB key: PON_CONTROLLER_SYSTEM_STATUS_OLT_ONU|<name>|<mac-address>|<onu-serial-number>.";
        leaf name {
          type string;
        }
        leaf mac-address {
          type leafref {
            path "/sp:sonic-pon/sp:PON_CONTROLLER_SYSTEM_STATUS_OLT/sp:PON_CONTROLLER_SYSTEM_STATUS_OLT_LIST/sp:mac-address";
          }
          description
            "References PON_CONTROLLER_SYSTEM_STATUS_OLT_LIST.";
        }
        leaf onu-serial-number {
          type string;
          description
            "ONU serial number (defined by Vendor ID + Vendor SN).";
        }
        leaf onu-state {
          type string;
          description
            "The current state of the ONU.";
        }
      }
    }
    container PON_OLT_INTF_STATE {
      description
        "PON_OLT_INTF_STATE table in StateDB.";
      config false;
      list PON_OLT_INTF_STATE_LIST {
        key "olt-intf-name";
        description
          "List of OLT interfaces.
           StateDB key: PON_OLT_INTF_STATE|<olt-intf-name>";
        leaf olt-intf-name {
          type string;
          description
            "Name identifier to reference this OLT interface.";
        }
        leaf timestamp {
          type yang:date-and-time;
          description
            "The last update for this state file";
        }
        leaf protection-role {
          type enumeration {
            enum active {
              description
                "This OLT interface is the active member of its protection group.";
            }
            enum standby {
              description
                "This OLT interface is the standby member of its protection group.";
            }
            enum unknown {
              description
                "Transient / detecting; role not yet determined.";
            }
          }
          description
            "Protection role of THIS OLT interface..";
        }
        leaf fiber-reach {
          type enumeration {
            enum extended-0to40km {
              description
                "Configure the OLT interface for extended fiber reach, supporting ONUs with a distance from 0 to 40 kilometers.";
            }
            enum extended-40to60km {
              description
                "Configure the OLT interface for extended fiber reach, supporting ONUs with a distance from 40 to 60 kilometers.";
            }
            enum extended-20to40km {
              description
                "Configure the OLT interface for extended fiber reach, supporting ONUs with a distance from 20 to 40 kilometers.";
            }
            enum extended-10to30km {
              description
                "Configure the OLT interface for extended fiber reach, supporting ONUs with a distance from 10 to 30 kilometers.";
            }
            enum short {
              description
                "Configure the OLT interface for short fiber reach, supporting ONUs with a distance from 0 to 10 kilometers.";
            }
            enum standard {
              description
                "Configure the OLT interface for standard fiber reach, supporting ONUs with a distance from 0 to 20 kilometers.";
            }
            enum olt-default {
              description
                "Use the fiber reach value configured in the OLT interface flash (persistent store).";
            }
          }
          description
            "The current fiber reach configured on this OLT interface.";
        }
        leaf laser-shutdown {
          type string;
          description
            "Indicates the cause of a laser shutdown";
        }
        leaf loss-of-signal {
          type boolean;
          description
            "There are no ONUs registered on the OLT interface";
        }
        leaf pon-enable {
          type boolean;
          description
            "Current state of PON Optics on the module.";
        }
        leaf discovery-period {
          type uint32;
          description
            "Current OLT interface discovery time interval.";
        }
        leaf downstream-fec {
          type boolean;
          description
            "Current Forward Error Correction in the downstream direction.";
        }
        leaf encryption {
          type spt:olt-encryption-mode;
          description
            "Current OLT interface PON MAC layer encryption mode";
        }
        leaf encryption-key-time {
          type uint16;
          units "seconds";
          description
            "Time between changing encryption keys.";
        }
        leaf error-detection-maximum-hec-ratio {
          type uint8;
          units "percent";
          description
            "Maximum percentage of HEC errors to disable an ONU.";
        }
        leaf error-detection-minimum-hec-sample {
          type uint16;
          units "GPON headers";
          description
            "Minimum number of HEC error samples to consider for error-detection-maximum-ratio.";
        }
        leaf error-detection-maximum-ratio {
          type uint8;
          units "percent";
          description
            "Maximum percentage of errored upstream bursts to disable an ONU.";
        }
        leaf error-detection-minimum-sample {
          type uint16;
          units "Upstream Bursts";
          description
            "Minumum number of upstream bursts to consider for error-detection-maximum-ratio.";
        }
        leaf guard-time {
          type uint32;
          description
            "Current dead time between upstream burst slots.";
        }
        leaf mac-address {
          type yang:mac-address;
          description
            "GPON MAC Address.";
        }
        leaf max-frame-size {
          type uint32;
          description
            "Current maximum frame size allowed at the PON receiver";
        }
        leaf pon-id {
          type uint32;
          description
            "Unique 32-bit value assigned to each PON.";
        }
        leaf pon-tag {
          type string;
          description
            "PON-TAG description in burst profile message";
        }
        leaf port-id {
          type string {
            length "0..256";
          }
        }
        leaf device-id {
          type string {
            length "0..256";
          }
        }
        leaf aging-time {
          type uint16;
          units "seconds";
          description
            "Dynamic MAC Address aging time. When the aging time expires, the address is removed from the Dynamic MAC learning table.";
        }
      }
    }
    container PON_OLT_INTF_ONU_STATE {
      description
        "PON_OLT_INTF_ONU_STATE table in StateDB.";
      config false;
      list PON_OLT_INTF_ONU_STATE_LIST {
        key "olt-intf-name onu-serial-number";
        description
          "ONU related status.
           StateDB key: PON_OLT_INTF_ONU_STATE|<olt-intf-name>|<onu-serial-number>.";
        leaf olt-intf-name {
          type leafref {
            path "/sp:sonic-pon/sp:PON_OLT_INTF_STATE/sp:PON_OLT_INTF_STATE_LIST/sp:olt-intf-name";
          }
          description
            "References PON_OLT_INTF_STATE_LIST.";
        }
        leaf onu-serial-number {
          type string;
          description
            "ONU serial number (defined by Vendor ID + Vendor SN).";
        }
        leaf onu-id {
          type uint16;
          description
            "The allocation ID, XGEM port ID, and ONU ID number assigned to this ONU to carry OMCI management messages.";
        }
        leaf disable {
          type boolean;
          description
            "When true, the disable serial number PLOAM message will be sent to this ONU if it tries to register.";
        }
        ordered-by system;
      }
    }
    container PON_OLT_INTF_ONU_FW_UPGRADE_STATE {
      description
        "PON_OLT_INTF_ONU_FW_UPGRADE_STATE table in StateDB.";
      config false;
      list PON_OLT_INTF_ONU_FW_UPGRADE_STATE_LIST {
        key "olt-intf-name onu-serial-number";
        description
          "The list of ONUs currently performing firmware upgrades on the OLT.
           StateDB key: PON_OLT_INTF_ONU_FW_UPGRADE_STATE|<olt-intf-name>|<onu-serial-number>.";
        leaf olt-intf-name {
          type leafref {
            path "/sp:sonic-pon/sp:PON_OLT_INTF_ONU_STATE/sp:PON_OLT_INTF_ONU_STATE_LIST/sp:olt-intf-name";
          }
          description
            "References PON_OLT_INTF_ONU_STATE_LIST.";
        }
        leaf onu-serial-number {
          type string;
          description
            "ONU device identifier (XGS-PON ONU serial number)";
        }
      }
    }
    container PON_OLT_INTF_ONU_OPERATIONAL_STATE {
      description
        "PON_OLT_INTF_ONU_OPERATIONAL_STATE table in StateDB.";
      config false;
      list PON_OLT_INTF_ONU_OPERATIONAL_STATE_LIST {
        key "olt-intf-name id";
        description
          "Consolidated list of ONUs with their operational state.
           StateDB key: PON_OLT_INTF_ONU_OPERATIONAL_STATE|<olt-intf-name>|<id>.";
        leaf olt-intf-name {
          type leafref {
            path "/sp:sonic-pon/sp:PON_OLT_INTF_ONU_STATE/sp:PON_OLT_INTF_ONU_STATE_LIST/sp:olt-intf-name";
          }
          description
            "References PON_OLT_INTF_ONU_STATE_LIST.";
        }
        leaf id {
          type string;
          description
            "ONU device identifier (XGS-PON ONU serial number)";
        }
        leaf operational-state {
          type enumeration {
            enum registered {
              description
                "ONU registered on OLT and specified in OLT configuration";
            }
            enum deregistered {
              description
                "ONU deregistered and specified in OLT configuration";
            }
            enum disabled {
              description
                "ONU deregistered due to disable serial number PLOAM";
            }
            enum disallowed-admin {
              description
                "ONU blocked by ONU Configuration file OLT specification";
            }
            enum disallowed-error {
              description
                "ONU blocked due to excessive upstream errors";
            }
            enum disallowed-registration-id {
              description
                "ONU blocked due to registration-id mismatch";
            }
            enum dying-gasp {
              description
                "ONU in dying gasp state (loss of power)";
            }
            enum unprovisioned {
              description
                "ONU not registered or not in OLT configuration";
            }
            enum unspecified {
              description
                "ONU registered but not specified in OLT configuration";
            }
            enum unknown {
              description
                "ONU state unknown or undefined";
            }
          }
          description
            "Current operational state of the ONU";
        }
      }
    }
    container PON_OLT_INTF_NETWORK_STATE {
      description
        "PON_OLT_INTF_NNI_NETWORK_STATE table in StateDB.";
      config false;
      list PON_OLT_INTF_NETWORK_STATE_LIST {
        key "olt-intf-name vlan-id";
        description
          "List of the NNI Networks configured on the OLT.
           StateDB key: PON_OLT_INTF_NETWORK_STATE|<olt-intf-name>|<vlan-id>.";
        leaf olt-intf-name {
          type leafref {
            path "/sp:sonic-pon/sp:PON_OLT_INTF_STATE/sp:PON_OLT_INTF_STATE_LIST/sp:olt-intf-name";
          }
          description
            "References PON_OLT_INTF_STATE_LIST.";
        }
        leaf network-id {
          type uint16;
          description
            "Index of entry.";
        }
        leaf learning-limit {
          type uint16;
          description
            "Dynamic MAC learning table size limit for this NNI Network. A value of '0' indicates that MAC Learning is disabled for this NNI Network.";
        }
        leaf pon-flood-id {
          type uint16;
          description
            "XGEM Port ID for unknown/multicast/broadcast frames from this network.";
        }
        leaf vlan-id {
          type uint16 {
            range "0..4095";
          }
          description
            "VLAN id used to identify packets on the NNI network";
        }
        leaf flooding-sla-downstream-guaranteed-rate {
          type uint32;
          units "kbps";
          description
            "Guaranteed (high priority) rate in kbps.";
        }
        leaf flooding-sla-downstream-guaranteed-maximum-burst {
          type uint32;
          units "kBytes";
          description
            "Maximum burst size in Kilobytes. The guaranteed rate is enforced at this burst size.";
        }
        leaf flooding-sla-downstream-best-effort-rate {
          type uint32;
          units "kbps";
          description
            "Best Effort (low priority) rate in kbps.";
        }
        leaf flooding-sla-downstream-best-effort-maximum-burst {
          type uint32;
          units "kBytes";
          description
            "Maximum burst size in Kilobytes. The best effort rate is enforced at this burst size.";
        }
      }
    }
    container PON_OLT_INTF_NNI_NETWORK_LEARNING_TABLE_STATE {
      description
        "PON_OLT_INTF_NNI_NETWORK_LEARNING_TABLE_STATE table in StateDB.";
      config false;
      list PON_OLT_INTF_NNI_NETWORK_LEARNING_TABLE_STATE_LIST {
        key "olt-intf-name network-id mac-address";
        description
          "The MAC address learning table for this uplink port.  A list of MAC Addresses and source XGEM port IDs (XGS-PON).
           StateDB key: PON_OLT_INTF_NNI_NETWORK_LEARNING_TABLE_STATE|<olt-intf-name>|<network-id>|<mac-address>.";
        leaf olt-intf-name {
          type leafref {
            path "/sp:sonic-pon/sp:PON_OLT_INTF_STATE/sp:PON_OLT_INTF_STATE_LIST/sp:olt-intf-name";
          }
          description
            "References PON_OLT_INTF_STATE_LIST.";
        }
        leaf network-id {
          type leafref {
            path "/sp:sonic-pon/sp:PON_OLT_INTF_NETWORK_STATE/sp:PON_OLT_INTF_NETWORK_STATE_LIST/sp:network-id";
          }
          description
            "References PON_OLT_INTF_NETWORK_STATE_LIST.";
        }
        leaf mac-address {
          type yang:mac-address;
          description
            "MAC address of the learned CPE.";
        }
        leaf unicast-id {
          type uint16;
          description
            "XGEM Port ID that the CPE was learned on.";
        }
      }
    }
    container PON_OLT_INTF_ONU_SERVICE_TCONT_STATE {
      description
        "PON_OLT_INTF_ONU_SERVICE_TCONT_STATE table in StateDB.";
      config false;
      list PON_OLT_INTF_ONU_SERVICE_TCONT_STATE_LIST {
        key "olt-intf-name onu-serial-number service-port-id";
        description
          "List of OLT Service ports.
           StateDB key: PON_OLT_INTF_ONU_SERVICE_TCONT_STATE|<olt-intf-name>|<onu-serial-number>|<service-port-id>.";
        leaf olt-intf-name {
          type leafref {
            path "/sp:sonic-pon/sp:PON_OLT_INTF_STATE/sp:PON_OLT_INTF_STATE_LIST/sp:olt-intf-name";
          }
          description
            "References PON_OLT_INTF_STATE_LIST.";
        }
        leaf onu-serial-number {
          type leafref {
            path "/sp:sonic-pon/sp:PON_OLT_INTF_ONU_STATE/sp:PON_OLT_INTF_ONU_STATE_LIST/sp:onu-serial-number";
          }
          description
            "References PON_OLT_INTF_ONU_STATE_LIST.";
        }
        leaf service-port-id {
          type uint32;
          description
            "OLT Service port number.";
        }
        leaf alloc-id {
          type uint16;
          description
            "Allocation ID and XGEM Port ID used on this service port.";
        }
        ordered-by system;
      }
    }
    container PON_OLT_INTF_ONU_SERVICE_GEMPORT_STATE {
      description
        "PON_OLT_INTF_ONU_SERVICE_GEMPORT_STATE table in StateDB.";
      config false;
      list PON_OLT_INTF_ONU_SERVICE_GEMPORT_STATE_LIST {
        key "olt-intf-name onu-serial-number service-port-id";
        description
          "List of OLT GEM ports.
           StateDB key: PON_OLT_INTF_ONU_SERVICE_GEMPORT_STATE|<olt-intf-name>|<onu-serial-number>|<service-port-id>.";
        leaf olt-intf-name {
          type leafref {
            path "/sp:sonic-pon/sp:PON_OLT_INTF_STATE/sp:PON_OLT_INTF_STATE_LIST/sp:olt-intf-name";
          }
          description
            "References PON_OLT_INTF_STATE_LIST.";
        }
        leaf onu-serial-number {
          type leafref {
            path "/sp:sonic-pon/sp:PON_OLT_INTF_ONU_STATE/sp:PON_OLT_INTF_ONU_STATE_LIST/sp:onu-serial-number";
          }
          description
            "References PON_OLT_INTF_ONU_STATE_LIST.";
        }
        leaf service-port-id {
          type uint32;
          description
            "OLT Service port number.";
        }
        leaf gemport-id {
          type uint16;
          description
            "GEM port ID for this service port.";
        }
        leaf tcont-ref {
          type leafref {
            path "/sp:sonic-pon/sp:PON_OLT_INTF_ONU_SERVICE_TCONT_STATE/sp:PON_OLT_INTF_ONU_SERVICE_TCONT_STATE_LIST/sp:service-port-id";
          }
          description
            "References PON_OLT_INTF_ONU_SERVICE_TCONT_STATE_LIST.";
        }
        ordered-by system;
      }
    }
    container PON_OLT_PROTECTION_GROUP_STATE {
      description
        "PON_OLT_PROTECTION_GROUP_STATE table in StateDB.";
      config false;
      list PON_OLT_PROTECTION_GROUP_STATE_LIST {
        key "group-name";
        description
          "List of OLT PON protection groups.";
        leaf group-name {
          description
            "Name identifier used to reference this PON protection group.";
          type string;
        }
        leaf protection-state {
          type enumeration {
            enum protecting {
              description
                "Protection group is active.";
            }
            enum degraded {
              description
                "Protection group is in a degraded, non-operational state.";
            }
          }
          description
            "Current PON protection state of this group.";
        }
        leaf last-failover-reason {
          type string;
          description
            "Reason for the last PON protection switchover.";
        }
        leaf last-failover-time {
          type yang:date-and-time;
          description
            "Timestamp of the last PON protection switchover.";
        }
      }
    }
    container PON_OLT_PLUG_FW_UPGRADE_STATUS {
      description
        "PON_OLT_PLUG_FW_UPGRADE_STATUS table in StateDB.";
      config false;
      list PON_OLT_PLUG_FW_UPGRADE_STATUS_LIST {
        key "name";
        description
          "Firmware upgrade status. If a firmware upgrade is currently in-progress, the current
           status is reported. Otherwise, the status is reported for the last firmware upgrade performed
           for this OLT plug.

           StateDB key: PON_OLT_PLUG_FW_UPGRADE_STATUS|<name>.";
        leaf name {
          type leafref {
            path "/sp:sonic-pon/sp:PON_OLT_PLUG_STATE/sp:PON_OLT_PLUG_STATE_LIST/sp:name";
          }
          description
            "References PON_OLT_PLUG_STATE_LIST.";
        }
        leaf bank {
          type uint16;
          description
            "Last firmware bank number (software download ME ID) firmware was downloaded to.";
        }
        leaf fx-code {
          type uint32;
          description
            "OLT plug Software Download error code.";
        }
        leaf file {
          type string;
          description
            "Name of the file to download.";
        }
        leaf status {
          type string;
          description
            "Software download status (Downloading, Success, Failed).";
        }
        leaf upgrade-duration {
          type string;
          description
            "Length of time in hours, minutes, and seconds for the OLT plug upgrade to complete.";
        }
        leaf upgrade-time {
          type yang:date-and-time;
          description
            "Timestamp reporting time the OLT plug was upgraded.";
        }
      }
    }
    container PON_OLT_PLUG_FW_BANK_VERSION_STATE {
      description
        "PON_OLT_PLUG_FW_BANK_VERSION_STATE table in StateDB.";
      config false;
      list PON_OLT_PLUG_FW_BANK_VERSION_STATE_LIST {
        key "name bank-id";
        description
          "The version of firmware in the 4 banks on the OLT.
           StateDB key: PON_OLT_PLUG_FW_BANK_VERSION_STATE|<name>|<bank-id>.";
        leaf name {
          type leafref {
            path "/sp:sonic-pon/sp:PON_OLT_PLUG_STATE/sp:PON_OLT_PLUG_STATE_LIST/sp:name";
          }
          description
            "References PON_OLT_PLUG_STATE_LIST.";
        }
        leaf bank-id {
          type uint8;
          description
            "Index for this entry.";
        }
        leaf version {
          type string;
          description
            "Firmwre version";
        }
        ordered-by system;
      }
    }
    container PON_OLT_INTF_STATISTICS_BINNED {
      description
        "PON_OLT_INTF_STATISTICS_BINNED table in StateDB.";
      config false;
      list PON_OLT_INTF_STATISTICS_BINNED_LIST {
        key "olt-intf-name olt-stats-id";
        description
          "List containing the statistics history for this device.
           StateDB key: PON_OLT_INTF_STATISTICS_BINNED|<olt-intf-name>|<olt-stats-id>.";
        leaf olt-intf-name {
          type leafref {
            path "/sp:sonic-pon/sp:PON_OLT_INTF_STATE/sp:PON_OLT_INTF_STATE_LIST/sp:olt-intf-name";
          }
          description
            "References PON_OLT_INTF_STATE_LIST.";
        }
        leaf olt-stats-id {
          type yang:date-and-time;
          description
            "Timestamp when the statistics were collected.";
        }
        leaf timestamp {
          type yang:date-and-time;
          description
            "Timestamp when the statistics were collected.";
        }
        leaf offline-onus-count {
          type uint64;
          description
            "Number of ONUs which were known to the OLT but are no longer active.
             This includes ONUs which are deregistered or have been disabled, administratively disallowed,
             disallowed due to too many errors detected from the ONU, or disallowed due to a mismatched PON Registration ID";
        }
        leaf online-onus-count {
          type uint64;
          description
            "Number of ONUs which are active. This includes ONUs which are registered or unspecified.";
        }
        leaf pon-fec-seconds {
          type uint64;
          description
            "Forward Error Correction on the PON in seconds";
        }
        leaf rx-bw-ethernet-rate-bps {
          type uint64;
          description
            "Receive BW Ethernet Rate bps";
        }
        leaf rx-bw-overhead-burst-bps {
          type uint64;
          description
            "Receive BW Overhead Burst bps";
        }
        leaf rx-bw-overhead-fec-bps {
          type uint64;
          description
            "Receive BW Overhead FEC bps";
        }
        leaf rx-bw-overhead-total-bps {
          type uint64;
          description
            "Receive BW Overhead Total bps";
        }
        leaf rx-bw-packet-used-bps {
          type uint64;
          description
            "Receive BW Packet Used bps";
        }
        leaf rx-bw-total-free-bps {
          type uint64;
          description
            "Receive BW Total Free bps";
        }
        leaf rx-bw-total-used-bps {
          type uint64;
          description
            "Receive BW Total Used bps";
        }
        leaf rx-bw-total-util {
          type uint64;
          description
            "Receive BW Total Util";
        }
        leaf rx-bandwidth-reqs {
          type uint64;
          description
            "Receive Bandwidth Reqs";
        }
        leaf rx-crc32-drops {
          type uint64;
          description
            "Receive CRC32 Drops";
        }
        leaf rx-crc8-errors {
          type uint64;
          description
            "Receive CRC8 Errors";
        }
        leaf rx-empty-slots {
          type uint64;
          description
            "Receive Empty Slots";
        }
        leaf rx-encrypted-frames {
          type uint64;
          description
            "Receive Encrypted Frames";
        }
        leaf rx-encrypted-octets {
          type uint64;
          description
            "Receive Encrypted Octets";
        }
        leaf rx-encrypted-segments {
          type uint64;
          description
            "Receive Encrypted Segments";
        }
        leaf rx-errored-bip-bits {
          type uint64;
          description
            "Receive Errored BIP Bits";
        }
        leaf rx-errored-bip-blocks {
          type uint64;
          description
            "Receive Errored BIP Blocks";
        }
        leaf rx-fec-corrected-blocks {
          type uint64;
          description
            "Receive FEC Corrected Blocks";
        }
        leaf rx-fec-corrections {
          type uint64;
          description
            "Receive FEC Corrections";
        }
        leaf rx-fec-good-blocks {
          type uint64;
          description
            "Receive FEC Good Blocks";
        }
        leaf rx-fec-uncorrectable-blocks {
          type uint64;
          description
            "Receive FEC Uncorrectable Blocks";
        }
        leaf rx-filtered-frames {
          type uint64;
          description
            "Receive Filtered Frames";
        }
        leaf rx-frames-1024_1518 {
          type uint64;
          description
            "Receive Frames 1024-1518";
        }
        leaf rx-frames-128_255 {
          type uint64;
          description
            "Receive Frames 128-255";
        }
        leaf rx-frames-1519_plus {
          type uint64;
          description
            "Receive Frames 1519-Plus";
        }
        leaf rx-frames-256_511 {
          type uint64;
          description
            "Receive Frames 256-511";
        }
        leaf rx-frames-512_1023 {
          type uint64;
          description
            "Receive Frames 512-1023";
        }
        leaf rx-frames-64 {
          type uint64;
          description
            "Receive Frames 64";
        }
        leaf rx-frames-65_127 {
          type uint64;
          description
            "Receive Frames 65-127";
        }
        leaf rx-frames-green {
          type uint64;
          description
            "Receive Frames Green";
        }
        leaf rx-good-bip-blocks {
          type uint64;
          description
            "Receive Good BIP Blocks";
        }
        leaf rx-hec-errors {
          type uint64;
          description
            "Receive HEC Errors";
        }
        leaf rx-idle-octets {
          type uint64;
          description
            "Receive Idle Octets";
        }
        leaf rx-mpcp-ploam {
          type uint64;
          description
            "Receive MPCP/PLOAM";
        }
        leaf rx-multi-broadcast-octets {
          type uint64;
          description
            "Receive Multi/Broadcast Octets";
        }
        leaf rx-omci-mic-errors {
          type uint64;
          description
            "Receive OMCI MIC Errors";
        }
        leaf rx-optical-level-idle {
          type decimal64 {
            fraction-digits 3;
          }
          units "dBm";
          description
            "Receive Optical Level Idle";
        }
        leaf rx-overflow-drops {
          type uint64;
          description
            "Receive Overflow Drops";
        }
        leaf rx-overflow-octets {
          type uint64;
          description
            "Receive Overflow Octets";
        }
        leaf rx-plain-frames {
          type uint64;
          description
            "Receive Plain Frames";
        }
        leaf rx-plain-octets {
          type uint64;
          description
            "Receive Plain Octets";
        }
        leaf rx-plain-segments {
          type uint64;
          description
            "Receive Plain Segments";
        }
        leaf rx-ploam-mic-errors {
          type uint64;
          description
            "Receive PLOAM MIC Errors";
        }
        leaf rx-too-long-drops {
          type uint64;
          description
            "Receive Too Long Drops";
        }
        leaf rx-too-short-drops {
          type uint64;
          description
            "Receive Too Short Drops";
        }
        leaf rx-total-octets {
          type uint64;
          description
            "Receive Total Octets";
        }
        leaf rx-unicast-octets {
          type uint64;
          description
            "Receive Unicast Octets";
        }
        leaf rx-unmatched-drops {
          type uint64;
          description
            "Receive Unmatched Drops";
        }
        leaf total-onus-count {
          type uint64;
          description
            "Number of ONUs which are known to the OLT. This includes both Online and Offline ONUs.";
        }
        leaf tx-bw-ethernet-rate-bps {
          type uint64;
          description
            "Transmit BW Ethernet Rate bps";
        }
        leaf tx-bw-overhead-fec-bps {
          type uint64;
          description
            "Transmit BW Overhead FEC bps";
        }
        leaf tx-bw-overhead-framing-bps {
          type uint64;
          description
            "Transmit BW Overhead Framing bps";
        }
        leaf tx-bw-overhead-total-bps {
          type uint64;
          description
            "Transmit BW Overhead Total bps";
        }
        leaf tx-bw-packet-used-bps {
          type uint64;
          description
            "Transmit BW Packet Used bps";
        }
        leaf tx-bw-total-free-bps {
          type uint64;
          description
            "Transmit BW Total Free bps";
        }
        leaf tx-bw-total-used-bps {
          type uint64;
          description
            "Transmit BW Total Used bps";
        }
        leaf tx-bw-total-util {
          type uint64;
          description
            "Transmit BW Total Util";
        }
        leaf tx-bandwidth-reqs {
          type uint64;
          description
            "Transmit Bandwidth Reqs";
        }
        leaf tx-encrypted-frames {
          type uint64;
          description
            "Transmit Encrypted Frames";
        }
        leaf tx-encrypted-octets {
          type uint64;
          description
            "Transmit Encrypted Octets";
        }
        leaf tx-encrypted-segments {
          type uint64;
          description
            "Transmit Encrypted Segments";
        }
        leaf tx-frames-1024_1518 {
          type uint64;
          description
            "Transmit Frames 1024-1518";
        }
        leaf tx-frames-128_255 {
          type uint64;
          description
            "Transmit Frames 128-255";
        }
        leaf tx-frames-1519_plus {
          type uint64;
          description
            "Transmit Frames 1519-Plus";
        }
        leaf tx-frames-256_511 {
          type uint64;
          description
            "Transmit Frames 256-511";
        }
        leaf tx-frames-512_1023 {
          type uint64;
          description
            "Transmit Frames 512-1023";
        }
        leaf tx-frames-64 {
          type uint64;
          description
            "Transmit Frames 64";
        }
        leaf tx-frames-65_127 {
          type uint64;
          description
            "Transmit Frames 65-127";
        }
        leaf tx-frames-broadcast {
          type uint64;
          description
            "Transmit Frames Broadcast";
        }
        leaf tx-frames-green {
          type uint64;
          description
            "Transmit Frames Green";
        }
        leaf tx-frames-multicast {
          type uint64;
          description
            "Transmit Frames Multicast";
        }
        leaf tx-frames-unicast {
          type uint64;
          description
            "Transmit Frames Unicast";
        }
        leaf tx-idle-octets {
          type uint64;
          description
            "Transmit Idle Octets";
        }
        leaf tx-mpcp-ploam {
          type uint64;
          description
            "Transmit MPCP/PLOAM";
        }
        leaf tx-multi-broadcast-octets {
          type uint64;
          description
            "Transmit Multi/Broadcast Octets";
        }
        leaf tx-oam {
          type uint64;
          description
            "Transmit OAM";
        }
        leaf tx-optical-level {
          type decimal64 {
            fraction-digits 3;
          }
          units "dBm";
          description
            "Transmit Optical Level";
        }
        leaf tx-plain-frames {
          type uint64;
          description
            "Transmit Plain Frames";
        }
        leaf tx-plain-octets {
          type uint64;
          description
            "Transmit Plain Octets";
        }
        leaf tx-plain-segments {
          type uint64;
          description
            "Transmit Plain Segments";
        }
        leaf tx-total-octets {
          type uint64;
          description
            "Transmit Total Octets";
        }
        leaf tx-unicast-octets {
          type uint64;
          description
            "Transmit Unicast Octets";
        }
        leaf uninventoried-onus-count {
          type uint64;
          description
            "Number of ONUs which are active but not inventoried.";
        }
        leaf unprovisioned-onus-count {
          type uint64;
          description
            "Number of ONUs which are currently unprovisioned.";
        }
      }
    }
    container PON_OLT_PLUG_STATISTICS_BINNED_ENV {
      description
        "PON_OLT_PLUG_STATISTICS_BINNED_ENV table in StateDB.";
      config false;
      list PON_OLT_PLUG_STATISTICS_BINNED_ENV_LIST {
        key "olt-name olt-stats-id";
        description
          "OLT device environmental statistics.
           StateDB key: PON_OLT_PLUG_STATISTICS_BINNED_ENV|<olt-name>|<olt-stats-id>.";
        leaf olt-name {
          type leafref {
            path "/sp:sonic-pon/sp:PON_OLT_INTF_STATE/sp:PON_OLT_INTF_STATE_LIST/sp:olt-intf-name";
          }
          description
            "References PON_OLT_INTF_STATE_LIST.";
        }
        leaf olt-stats-id {
          type leafref {
            path "/sp:sonic-pon/sp:PON_OLT_INTF_STATISTICS_BINNED/sp:PON_OLT_INTF_STATISTICS_BINNED_LIST/sp:olt-stats-id";
          }
          description
            "References PON_OLT_INTF_STATISTICS_BINNED_LIST.";
        }
        leaf current {
          type decimal64 {
            fraction-digits 3;
          }
          units "microamp";
          description
            "Current";
        }
        leaf transmit-bias {
          type decimal64 {
            fraction-digits 3;
          }
          units "microamp";
          description
            "Transmit Bias";
        }
        leaf voltage {
          type decimal64 {
            fraction-digits 3;
          }
          units "millivolt";
          description
            "Voltage";
        }
      }
    }
    container PON_OLT_PLUG_STATISTICS_BINNED_NNI {
      description
        "PON_OLT_PLUG_STATISTICS_BINNED_NNI table in StateDB.";
      config false;
      list PON_OLT_PLUG_STATISTICS_BINNED_NNI_LIST {
        key "olt-name olt-stats-id";
        description
          "OLT plug NNI port statistics.
           StateDB key: PON_OLT_PLUG_STATISTICS_BINNED_NNI|<olt-name>|<olt-stats-id>.";
        leaf olt-name {
          type leafref {
            path "/sp:sonic-pon/sp:PON_OLT_INTF_STATE/sp:PON_OLT_INTF_STATE_LIST/sp:olt-intf-name";
          }
          description
            "References PON_OLT_INTF_STATE_LIST.";
        }
        leaf olt-stats-id {
          type leafref {
            path "/sp:sonic-pon/sp:PON_OLT_INTF_STATISTICS_BINNED/sp:PON_OLT_INTF_STATISTICS_BINNED_LIST/sp:olt-stats-id";
          }
          description
            "References PON_OLT_INTF_STATISTICS_BINNED_LIST.";
        }
        leaf rx-broadcast-octets {
          type uint64;
          description
            "Receive Broadcast Octets";
        }
        leaf rx-crc32-drops {
          type uint64;
          description
            "Receive CRC32 Drops";
        }
        leaf rx-encrypted-frames {
          type uint64;
          description
            "Receive Encrypted Frames";
        }
        leaf rx-encrypted-octets {
          type uint64;
          description
            "Receive Encrypted Octets";
        }
        leaf rx-filtered-frames {
          type uint64;
          description
            "Receive Filtered Frames";
        }
        leaf rx-frames-1024_1518 {
          type uint64;
          description
            "Receive Frames 1024-1518";
        }
        leaf rx-frames-128_255 {
          type uint64;
          description
            "Receive Frames 128-255";
        }
        leaf rx-frames-1519_plus {
          type uint64;
          description
            "Receive Frames 1519-Plus";
        }
        leaf rx-frames-256_511 {
          type uint64;
          description
            "Receive Frames 256-511";
        }
        leaf rx-frames-512_1023 {
          type uint64;
          description
            "Receive Frames 512-1023";
        }
        leaf rx-frames-64 {
          type uint64;
          description
            "Receive Frames 64";
        }
        leaf rx-frames-65_127 {
          type uint64;
          description
            "Receive Frames 65-127";
        }
        leaf rx-frames-broadcast {
          type uint64;
          description
            "Receive Frames Broadcast";
        }
        leaf rx-frames-green {
          type uint64;
          description
            "Receive Frames Green";
        }
        leaf rx-frames-multicast {
          type uint64;
          description
            "Receive Frames Multicast";
        }
        leaf rx-frames-unicast {
          type uint64;
          description
            "Receive Frames Unicast";
        }
        leaf rx-multicast-octets {
          type uint64;
          description
            "Receive Multicast Octets";
        }
        leaf rx-oam {
          type uint64;
          description
            "Receive OAM";
        }
        leaf rx-oam-octets {
          type uint64;
          description
            "Receive OAM Octets";
        }
        leaf rx-other-cascading-bytes {
          type uint64;
          description
            "Receive Other Cascading Bytes";
        }
        leaf rx-other-cascading-packets {
          type uint64;
          description
            "Receive Other Cascading Packets";
        }
        leaf rx-overflow-drops {
          type uint64;
          description
            "Receive Overflow Drops";
        }
        leaf rx-overflow-octets {
          type uint64;
          description
            "Receive Overflow Octets";
        }
        leaf rx-plain-frames {
          type uint64;
          description
            "Receive Plain Frames";
        }
        leaf rx-plain-octets {
          type uint64;
          description
            "Receive Plain Octets";
        }
        leaf rx-too-long-drops {
          type uint64;
          description
            "Receive Too Long Drops";
        }
        leaf rx-too-short-drops {
          type uint64;
          description
            "Receive Too Short Drops";
        }
        leaf rx-unicast-octets {
          type uint64;
          description
            "Receive Unicast Octets";
        }
        leaf tomi-requests {
          type uint64;
          description
            "TOMI Requests";
        }
        leaf tomi-resp-time-avg {
          type uint64;
          units "microseconds";
          description
            "TOMI Resp Time Avg";
        }
        leaf tomi-resp-time-max {
          type uint64;
          units "microseconds";
          description
            "TOMI Resp Time Max";
        }
        leaf tomi-resp-time-min {
          type uint64;
          units "microseconds";
          description
            "TOMI Resp Time Min";
        }
        leaf tomi-responses {
          type uint64;
          description
            "TOMI Responses";
        }
        leaf tomi-time-to-send-avg {
          type uint64;
          units "microseconds";
          description
            "TOMI Time to Send Avg";
        }
        leaf tomi-time-to-send-max {
          type uint64;
          units "microseconds";
          description
            "TOMI Time to Send Max";
        }
        leaf tomi-time-to-send-min {
          type uint64;
          units "microseconds";
          description
            "TOMI Time to Send Min";
        }
        leaf tomi-timeouts {
          type uint64;
          description
            "TOMI Timeouts";
        }
        leaf tx-broadcast-octets {
          type uint64;
          description
            "Transmit Broadcast Octets";
        }
        leaf tx-cascading-bytes {
          type uint64;
          description
            "Transmit Cascading Bytes";
        }
        leaf tx-cascading-packets {
          type uint64;
          description
            "Transmit Cascading Packets";
        }
        leaf tx-encrypted-frames {
          type uint64;
          description
            "Transmit Encrypted Frames";
        }
        leaf tx-frames-1024_1518 {
          type uint64;
          description
            "Transmit Frames 1024-1518";
        }
        leaf tx-frames-128_255 {
          type uint64;
          description
            "Transmit Frames 128-255";
        }
        leaf tx-frames-1519_plus {
          type uint64;
          description
            "Transmit Frames 1519-Plus";
        }
        leaf tx-frames-256_511 {
          type uint64;
          description
            "Transmit Frames 256-511";
        }
        leaf tx-frames-512_1023 {
          type uint64;
          description
            "Transmit Frames 512-1023";
        }
        leaf tx-frames-64 {
          type uint64;
          description
            "Transmit Frames 64";
        }
        leaf tx-frames-65_127 {
          type uint64;
          description
            "Transmit Frames 65-127";
        }
        leaf tx-frames-broadcast {
          type uint64;
          description
            "Transmit Frames Broadcast";
        }
        leaf tx-frames-green {
          type uint64;
          description
            "Transmit Frames Green";
        }
        leaf tx-frames-multicast {
          type uint64;
          description
            "Transmit Frames Multicast";
        }
        leaf tx-frames-unicast {
          type uint64;
          description
            "Transmit Frames Unicast";
        }
        leaf tx-multicast-octets {
          type uint64;
          description
            "Transmit Multicast Octets";
        }
        leaf tx-non_control-octets {
          type uint64;
          description
            "Transmit Non-Control Octets";
        }
        leaf tx-oam {
          type uint64;
          description
            "Transmit OAM";
        }
        leaf tx-oam-octets {
          type uint64;
          description
            "Transmit OAM Octets";
        }
        leaf tx-plain-frames {
          type uint64;
          description
            "Transmit Plain Frames";
        }
        leaf tx-unicast-octets {
          type uint64;
          description
            "Transmit Unicast Octets";
        }
      }
    }
    container PON_OLT_PLUG_STATISTICS_BINNED_TEMP {
      description
        "PON_OLT_PLUG_STATISTICS_BINNED_TEMP table in StateDB.";
      config false;
      list PON_OLT_PLUG_STATISTICS_BINNED_TEMP_LIST {
        key "olt-name olt-stats-id";
        description
          "OLT plug device temperatures.
           StateDB key: PON_OLT_PLUG_STATISTICS_BINNED_TEMP|<olt-name>|<olt-stats-id>.";
        leaf olt-name {
          type leafref {
            path "/sp:sonic-pon/sp:PON_OLT_INTF_STATE/sp:PON_OLT_INTF_STATE_LIST/sp:olt-intf-name";
          }
          description
            "References PON_OLT_INTF_STATE_LIST.";
        }
        leaf olt-stats-id {
          type leafref {
            path "/sp:sonic-pon/sp:PON_OLT_INTF_STATISTICS_BINNED/sp:PON_OLT_INTF_STATISTICS_BINNED_LIST/sp:olt-stats-id";
          }
          description
            "References PON_OLT_INTF_STATISTICS_BINNED_LIST.";
        }
        leaf asic {
          type uint64;
          units "degrees celsius";
          description
            "ASIC temperature";
        }
        leaf laser {
          type uint64;
          units "degrees celsius";
          description
            "Laser temperature";
        }
        leaf xcvr {
          type uint64;
          units "degrees celsius";
          description
            "Transceiver temperature";
        }
      }
    }
    container PON_OLT_STATISTICS_BINNED_PON_FLOODING {
      description
        "PON_OLT_STATISTICS_BINNED_PON_FLOODING table in StateDB.";
      config false;
      list PON_OLT_STATISTICS_BINNED_PON_FLOODING_LIST {
        key "olt-name olt-stats-id flood-id";
        description
          "OLT PON Flooding (link) statistics.
           StateDB key: PON_OLT_STATISTICS_BINNED_PON_FLOODING|<olt-name>|<olt-stats-id>|<flood-id>.";
        leaf olt-name {
          type leafref {
            path "/sp:sonic-pon/sp:PON_OLT_INTF_STATE/sp:PON_OLT_INTF_STATE_LIST/sp:olt-intf-name";
          }
          description
            "References PON_OLT_INTF_STATE_LIST.";
        }
        leaf olt-stats-id {
          type leafref {
            path "/sp:sonic-pon/sp:PON_OLT_INTF_STATISTICS_BINNED/sp:PON_OLT_INTF_STATISTICS_BINNED_LIST/sp:olt-stats-id";
          }
          description
            "References PON_OLT_INTF_STATISTICS_BINNED_LIST.";
        }
        leaf flood-id {
          type uint16;
          description
            "OLT PON Flood ID (GPON: Multicast XGEM Port ID).";
        }
        leaf tx-bw-best-effort-sla-util {
          type uint64;
          description
            "Transmit BW Best Effort SLA Util";
        }
        leaf tx-bw-best-effort-sla-bps {
          type uint64;
          description
            "Transmit BW Best Effort SLA bps";
        }
        leaf tx-bw-guaranteed-sla-util {
          type uint64;
          description
            "Transmit BW Guaranteed SLA Util";
        }
        leaf tx-bw-guaranteed-sla-bps {
          type uint64;
          description
            "Transmit BW Guaranteed SLA bps";
        }
        leaf tx-bw-total-sla-util {
          type uint64;
          description
            "Transmit BW Total SLA Util";
        }
        leaf tx-bw-total-sla-bps {
          type uint64;
          description
            "Transmit BW Total SLA bps";
        }
        leaf tx-encrypted-octets {
          type uint64;
          description
            "Transmit Encrypted Octets";
        }
        leaf tx-frames-1024_1518 {
          type uint64;
          description
            "Transmit Frames 1024-1518";
        }
        leaf tx-frames-128_255 {
          type uint64;
          description
            "Transmit Frames 128-255";
        }
        leaf tx-frames-1519_plus {
          type uint64;
          description
            "Transmit Frames 1519-Plus";
        }
        leaf tx-frames-256_511 {
          type uint64;
          description
            "Transmit Frames 256-511";
        }
        leaf tx-frames-512_1023 {
          type uint64;
          description
            "Transmit Frames 512-1023";
        }
        leaf tx-frames-64 {
          type uint64;
          description
            "Transmit Frames 64";
        }
        leaf tx-frames-65_127 {
          type uint64;
          description
            "Transmit Frames 65-127";
        }
        leaf tx-frames-broadcast {
          type uint64;
          description
            "Transmit Frames Broadcast";
        }
        leaf tx-frames {
          type uint64;
          description
            "Transmit Frames";
        }
        leaf tx-frames-multicast {
          type uint64;
          description
            "Transmit Frames Multicast";
        }
        leaf tx-frames-unicast {
          type uint64;
          description
            "Transmit Frames Unicast";
        }
        leaf tx-multi-broadcast-octets {
          type uint64;
          description
            "Transmit Multi/Broadcast Octets";
        }
        leaf tx-plain-octets {
          type uint64;
          description
            "Transmit Plain Octets";
        }
        leaf tx-rate-bps {
          type uint64;
          description
            "Transmit Rate bps";
        }
        leaf tx-total-octets {
          type uint64;
          description
            "Transmit Total Octets";
        }
        leaf tx-unicast-octets {
          type uint64;
          description
            "Transmit Unicast Octets";
        }
      }
    }
    container PON_OLT_STATISTICS_BINNED_PON_FLOODING_NETWORK {
      description
        "PON_OLT_STATISTICS_BINNED_PON_FLOODING_NETWORK table in StateDB.";
      config false;
      list PON_OLT_STATISTICS_BINNED_PON_FLOODING_NETWORK_LIST {
        key "olt-name olt-stats-id flood-id";
        description
          "List of VLAN Tags identifying the NNI Networks using this PON Flood ID.
           StateDB key: PON_OLT_STATISTICS_BINNED_PON_FLOODING_NETWORK|<olt-name>|<olt-stats-id>|<flood-id>.";
        leaf olt-name {
          type leafref {
            path "/sp:sonic-pon/sp:PON_OLT_INTF_STATE/sp:PON_OLT_INTF_STATE_LIST/sp:olt-intf-name";
          }
          description
            "References PON_OLT_INTF_STATE_LIST.";
        }
        leaf olt-stats-id {
          type leafref {
            path "/sp:sonic-pon/sp:PON_OLT_INTF_STATISTICS_BINNED/sp:PON_OLT_INTF_STATISTICS_BINNED_LIST/sp:olt-stats-id";
          }
          description
            "References PON_OLT_INTF_STATISTICS_BINNED_LIST.";
        }
        leaf flood-id {
          type leafref {
            path "/sp:sonic-pon/sp:PON_OLT_STATISTICS_BINNED_PON_FLOODING/sp:PON_OLT_STATISTICS_BINNED_PON_FLOODING_LIST/sp:flood-id";
          }
          description
            "References PON_OLT_STATISTICS_BINNED_PON_FLOODING_LIST.";
        }
        leaf-list vlan-id {
          type uint16 {
            range "0..4095";
          }
          description
            "Network VLAN ID list.";
        }
      }
    }
    container PON_OLT_STATISTICS_ACCUMULATING_ENV {
      description
        "PON_OLT_STATISTICS_ACCUMULATING_ENV table in CounterDB.";
      config false;
      list PON_OLT_STATISTICS_ACCUMULATING_ENV_LIST {
        key "olt-name";
        description
          "OLT device environmental statistics.
           CounterDB key: PON_OLT_STATISTICS_ACCUMULATING_ENV|<olt-name>.";
        leaf olt-name {
          type leafref {
            path "/sp:sonic-pon/sp:PON_OLT_INTF_STATE/sp:PON_OLT_INTF_STATE_LIST/sp:olt-intf-name";
          }
          description
            "References PON_OLT_INTF_STATE_LIST.";
        }
        leaf current {
          type decimal64 {
            fraction-digits 3;
          }
          units "microamp";
          description
            "Current";
        }
        leaf transmit-bias {
          type decimal64 {
            fraction-digits 3;
          }
          units "microamp";
          description
            "Transmit Bias";
        }
        leaf voltage {
          type decimal64 {
            fraction-digits 3;
          }
          units "millivolt";
          description
            "Voltage";
        }
      }
    }
    container PON_OLT_STATISTICS_ACCUMULATING {
      description
        "PON_OLT_STATISTICS_ACCUMULATING table in CounterDB.";
      config false;
      list PON_OLT_STATISTICS_ACCUMULATING_LIST {
        key "olt-name";
        description
          "OLT PON port statistics.
           CounterDB key: PON_OLT_STATISTICS_ACCUMULATING|<olt-name>.";
        leaf olt-name {
          type leafref {
            path "/sp:sonic-pon/sp:PON_OLT_INTF_STATE/sp:PON_OLT_INTF_STATE_LIST/sp:olt-intf-name";
          }
          description
            "References PON_OLT_INTF_STATE_LIST.";
        }
        leaf offline-onus-count {
          type uint64;
          description
            "Number of ONUs which were known to the OLT but are no longer active.
             This includes ONUs which are deregistered or have been disabled, administratively disallowed,
             disallowed due to too many errors detected from the ONU, or disallowed due to a mismatched PON Registration ID";
        }
        leaf online-onus-count {
          type uint64;
          description
            "Number of ONUs which are active. This includes ONUs which are registered or unspecified.";
        }
        leaf pon-fec-seconds {
          type uint64;
          description
            "Forward Error Correction on the PON in seconds";
        }
        leaf rx-bw-ethernet-rate-bps {
          type uint64;
          description
            "Receive BW Ethernet Rate bps";
        }
        leaf rx-bw-overhead-burst-bps {
          type uint64;
          description
            "Receive BW Overhead Burst bps";
        }
        leaf rx-bw-overhead-fec-bps {
          type uint64;
          description
            "Receive BW Overhead FEC bps";
        }
        leaf rx-bw-overhead-total-bps {
          type uint64;
          description
            "Receive BW Overhead Total bps";
        }
        leaf rx-bw-packet-used-bps {
          type uint64;
          description
            "Receive BW Packet Used bps";
        }
        leaf rx-bw-total-free-bps {
          type uint64;
          description
            "Receive BW Total Free bps";
        }
        leaf rx-bw-total-used-bps {
          type uint64;
          description
            "Receive BW Total Used bps";
        }
        leaf rx-bw-total-util {
          type uint64;
          description
            "Receive BW Total Util";
        }
        leaf rx-bandwidth-reqs {
          type uint64;
          description
            "Receive Bandwidth Reqs";
        }
        leaf rx-crc32-drops {
          type uint64;
          description
            "Receive CRC32 Drops";
        }
        leaf rx-crc8-errors {
          type uint64;
          description
            "Receive CRC8 Errors";
        }
        leaf rx-empty-slots {
          type uint64;
          description
            "Receive Empty Slots";
        }
        leaf rx-encrypted-frames {
          type uint64;
          description
            "Receive Encrypted Frames";
        }
        leaf rx-encrypted-octets {
          type uint64;
          description
            "Receive Encrypted Octets";
        }
        leaf rx-encrypted-segments {
          type uint64;
          description
            "Receive Encrypted Segments";
        }
        leaf rx-errored-bip-bits {
          type uint64;
          description
            "Receive Errored BIP Bits";
        }
        leaf rx-errored-bip-blocks {
          type uint64;
          description
            "Receive Errored BIP Blocks";
        }
        leaf rx-fec-corrected-blocks {
          type uint64;
          description
            "Receive FEC Corrected Blocks";
        }
        leaf rx-fec-corrections {
          type uint64;
          description
            "Receive FEC Corrections";
        }
        leaf rx-fec-good-blocks {
          type uint64;
          description
            "Receive FEC Good Blocks";
        }
        leaf rx-fec-uncorrectable-blocks {
          type uint64;
          description
            "Receive FEC Uncorrectable Blocks";
        }
        leaf rx-filtered-frames {
          type uint64;
          description
            "Receive Filtered Frames";
        }
        leaf rx-frames-1024_1518 {
          type uint64;
          description
            "Receive Frames 1024-1518";
        }
        leaf rx-frames-128_255 {
          type uint64;
          description
            "Receive Frames 128-255";
        }
        leaf rx-frames-1519_plus {
          type uint64;
          description
            "Receive Frames 1519-Plus";
        }
        leaf rx-frames-256_511 {
          type uint64;
          description
            "Receive Frames 256-511";
        }
        leaf rx-frames-512_1023 {
          type uint64;
          description
            "Receive Frames 512-1023";
        }
        leaf rx-frames-64 {
          type uint64;
          description
            "Receive Frames 64";
        }
        leaf rx-frames-65_127 {
          type uint64;
          description
            "Receive Frames 65-127";
        }
        leaf rx-frames-green {
          type uint64;
          description
            "Receive Frames Green";
        }
        leaf rx-good-bip-blocks {
          type uint64;
          description
            "Receive Good BIP Blocks";
        }
        leaf rx-hec-errors {
          type uint64;
          description
            "Receive HEC Errors";
        }
        leaf rx-idle-octets {
          type uint64;
          description
            "Receive Idle Octets";
        }
        leaf rx-mpcp-ploam {
          type uint64;
          description
            "Receive MPCP/PLOAM";
        }
        leaf rx-multi-broadcast-octets {
          type uint64;
          description
            "Receive Multi/Broadcast Octets";
        }
        leaf rx-omci-mic-errors {
          type uint64;
          description
            "Receive OMCI MIC Errors";
        }
        leaf rx-optical-level-idle {
          type decimal64 {
            fraction-digits 3;
          }
          units "dBm";
          description
            "Receive Optical Level Idle";
        }
        leaf rx-overflow-drops {
          type uint64;
          description
            "Receive Overflow Drops";
        }
        leaf rx-overflow-octets {
          type uint64;
          description
            "Receive Overflow Octets";
        }
        leaf rx-plain-frames {
          type uint64;
          description
            "Receive Plain Frames";
        }
        leaf rx-plain-octets {
          type uint64;
          description
            "Receive Plain Octets";
        }
        leaf rx-plain-segments {
          type uint64;
          description
            "Receive Plain Segments";
        }
        leaf rx-ploam-mic-errors {
          type uint64;
          description
            "Receive PLOAM MIC Errors";
        }
        leaf rx-too-long-drops {
          type uint64;
          description
            "Receive Too Long Drops";
        }
        leaf rx-too-short-drops {
          type uint64;
          description
            "Receive Too Short Drops";
        }
        leaf rx-total-octets {
          type uint64;
          description
            "Receive Total Octets";
        }
        leaf rx-unicast-octets {
          type uint64;
          description
            "Receive Unicast Octets";
        }
        leaf rx-unmatched-drops {
          type uint64;
          description
            "Receive Unmatched Drops";
        }
        leaf total-onus-count {
          type uint64;
          description
            "Number of ONUs which are known to the OLT. This includes both Online and Offline ONUs.";
        }
        leaf tx-bw-ethernet-rate-bps {
          type uint64;
          description
            "Transmit BW Ethernet Rate bps";
        }
        leaf tx-bw-overhead-fec-bps {
          type uint64;
          description
            "Transmit BW Overhead FEC bps";
        }
        leaf tx-bw-overhead-framing-bps {
          type uint64;
          description
            "Transmit BW Overhead Framing bps";
        }
        leaf tx-bw-overhead-total-bps {
          type uint64;
          description
            "Transmit BW Overhead Total bps";
        }
        leaf tx-bw-packet-used-bps {
          type uint64;
          description
            "Transmit BW Packet Used bps";
        }
        leaf tx-bw-total-free-bps {
          type uint64;
          description
            "Transmit BW Total Free bps";
        }
        leaf tx-bw-total-used-bps {
          type uint64;
          description
            "Transmit BW Total Used bps";
        }
        leaf tx-bw-total-util {
          type uint64;
          description
            "Transmit BW Total Util";
        }
        leaf tx-bandwidth-reqs {
          type uint64;
          description
            "Transmit Bandwidth Reqs";
        }
        leaf tx-encrypted-frames {
          type uint64;
          description
            "Transmit Encrypted Frames";
        }
        leaf tx-encrypted-octets {
          type uint64;
          description
            "Transmit Encrypted Octets";
        }
        leaf tx-encrypted-segments {
          type uint64;
          description
            "Transmit Encrypted Segments";
        }
        leaf tx-frames-1024_1518 {
          type uint64;
          description
            "Transmit Frames 1024-1518";
        }
        leaf tx-frames-128_255 {
          type uint64;
          description
            "Transmit Frames 128-255";
        }
        leaf tx-frames-1519_plus {
          type uint64;
          description
            "Transmit Frames 1519-Plus";
        }
        leaf tx-frames-256_511 {
          type uint64;
          description
            "Transmit Frames 256-511";
        }
        leaf tx-frames-512_1023 {
          type uint64;
          description
            "Transmit Frames 512-1023";
        }
        leaf tx-frames-64 {
          type uint64;
          description
            "Transmit Frames 64";
        }
        leaf tx-frames-65_127 {
          type uint64;
          description
            "Transmit Frames 65-127";
        }
        leaf tx-frames-broadcast {
          type uint64;
          description
            "Transmit Frames Broadcast";
        }
        leaf tx-frames-green {
          type uint64;
          description
            "Transmit Frames Green";
        }
        leaf tx-frames-multicast {
          type uint64;
          description
            "Transmit Frames Multicast";
        }
        leaf tx-frames-unicast {
          type uint64;
          description
            "Transmit Frames Unicast";
        }
        leaf tx-idle-octets {
          type uint64;
          description
            "Transmit Idle Octets";
        }
        leaf tx-mpcp-ploam {
          type uint64;
          description
            "Transmit MPCP/PLOAM";
        }
        leaf tx-multi-broadcast-octets {
          type uint64;
          description
            "Transmit Multi/Broadcast Octets";
        }
        leaf tx-oam {
          type uint64;
          description
            "Transmit OAM";
        }
        leaf tx-optical-level {
          type decimal64 {
            fraction-digits 3;
          }
          units "dBm";
          description
            "Transmit Optical Level";
        }
        leaf tx-plain-frames {
          type uint64;
          description
            "Transmit Plain Frames";
        }
        leaf tx-plain-octets {
          type uint64;
          description
            "Transmit Plain Octets";
        }
        leaf tx-plain-segments {
          type uint64;
          description
            "Transmit Plain Segments";
        }
        leaf tx-total-octets {
          type uint64;
          description
            "Transmit Total Octets";
        }
        leaf tx-unicast-octets {
          type uint64;
          description
            "Transmit Unicast Octets";
        }
        leaf uninventoried-onus-count {
          type uint64;
          description
            "Number of ONUs which are active but not inventoried.";
        }
        leaf unprovisioned-onus-count {
          type uint64;
          description
            "Number of ONUs which are currently unprovisioned.";
        }
      }
    }
    container PON_OLT_STATISTICS_ACCUMULATING_TEMP {
      description
        "PON_OLT_STATISTICS_ACCUMULATING_TEMP table in CounterDB.";
      config false;
      list PON_OLT_STATISTICS_ACCUMULATING_TEMP_LIST {
        key "olt-name";
        description
          "OLT plug temperatures.
           CounterDB key: PON_OLT_STATISTICS_ACCUMULATING_TEMP|<olt-name>.";
        leaf olt-name {
          type leafref {
            path "/sp:sonic-pon/sp:PON_OLT_INTF_STATE/sp:PON_OLT_INTF_STATE_LIST/sp:olt-intf-name";
          }
          description
            "References PON_OLT_INTF_STATE_LIST.";
        }
        leaf asic {
          type uint64;
          units "degrees celsius";
          description
            "ASIC temperature";
        }
        leaf laser {
          type uint64;
          units "degrees celsius";
          description
            "Laser temperature";
        }
        leaf xcvr {
          type uint64;
          units "degrees celsius";
          description
            "Transceiver temperature";
        }
      }
    }
    container PON_OLT_STATISTICS_ACCUMULATING_PON_FLOODING {
      description
        "PON_OLT_STATISTICS_ACCUMULATING_PON_FLOODING table in CounterDB.";
      config false;
      list PON_OLT_STATISTICS_ACCUMULATING_PON_FLOODING_LIST {
        key "olt-name olt-id";
        description
          "OLT PON Flooding (link) statistics.
           CounterDB key: PON_OLT_STATISTICS_ACCUMULATING_PON_FLOODING|<olt-name>|<olt-id>.";
        leaf olt-name {
          type leafref {
            path "/sp:sonic-pon/sp:PON_OLT_INTF_STATE/sp:PON_OLT_INTF_STATE_LIST/sp:olt-intf-name";
          }
          description
            "References PON_OLT_INTF_STATE_LIST.";
        }
        leaf olt-id {
          type uint16;
          description
            "OLT PON Flood ID (GPON: Multicast XGEM Port ID).";
        }
        leaf tx-bw-best-effort-sla-util {
          type uint64;
          description
            "Transmit BW Best Effort SLA Util";
        }
        leaf tx-bw-best-effort-sla-bps {
          type uint64;
          description
            "Transmit BW Best Effort SLA bps";
        }
        leaf tx-bw-guaranteed-sla-util {
          type uint64;
          description
            "Transmit BW Guaranteed SLA Util";
        }
        leaf tx-bw-guaranteed-sla-bps {
          type uint64;
          description
            "Transmit BW Guaranteed SLA bps";
        }
        leaf tx-bw-total-sla-util {
          type uint64;
          description
            "Transmit BW Total SLA Util";
        }
        leaf tx-bw-total-sla-bps {
          type uint64;
          description
            "Transmit BW Total SLA bps";
        }
        leaf tx-encrypted-octets {
          type uint64;
          description
            "Transmit Encrypted Octets";
        }
        leaf tx-frames-1024_1518 {
          type uint64;
          description
            "Transmit Frames 1024-1518";
        }
        leaf tx-frames-128_255 {
          type uint64;
          description
            "Transmit Frames 128-255";
        }
        leaf tx-frames-1519_plus {
          type uint64;
          description
            "Transmit Frames 1519-Plus";
        }
        leaf tx-frames-256_511 {
          type uint64;
          description
            "Transmit Frames 256-511";
        }
        leaf tx-frames-512_1023 {
          type uint64;
          description
            "Transmit Frames 512-1023";
        }
        leaf tx-frames-64 {
          type uint64;
          description
            "Transmit Frames 64";
        }
        leaf tx-frames-65_127 {
          type uint64;
          description
            "Transmit Frames 65-127";
        }
        leaf tx-frames-broadcast {
          type uint64;
          description
            "Transmit Frames Broadcast";
        }
        leaf tx-frames {
          type uint64;
          description
            "Transmit Frames";
        }
        leaf tx-frames-multicast {
          type uint64;
          description
            "Transmit Frames Multicast";
        }
        leaf tx-frames-unicast {
          type uint64;
          description
            "Transmit Frames Unicast";
        }
        leaf tx-multi-broadcast-octets {
          type uint64;
          description
            "Transmit Multi/Broadcast Octets";
        }
        leaf tx-plain-octets {
          type uint64;
          description
            "Transmit Plain Octets";
        }
        leaf tx-rate-bps {
          type uint64;
          description
            "Transmit Rate bps";
        }
        leaf tx-total-octets {
          type uint64;
          description
            "Transmit Total Octets";
        }
        leaf tx-unicast-octets {
          type uint64;
          description
            "Transmit Unicast Octets";
        }
      }
    }
    container PON_OLT_STATISTICS_ACCUMULATING_PON_FLOODING_NNI_NETWORK {
      description
        "PON_OLT_STATISTICS_ACCUMULATING_PON_FLOODING_NNI_NETWORK table in CounterDB.";
      config false;
      list PON_OLT_STATISTICS_ACCUMULATING_PON_FLOODING_NNI_NETWORK_LIST {
        key "olt-name olt-id";
        description
          "List of VLAN Tags identifying the NNI Networks using this PON Flood ID.
           CounterDB key: PON_OLT_STATISTICS_ACCUMULATING_PON_FLOODING_NNI_NETWORK|<olt-name>|<olt-id>.";
        leaf olt-name {
          type leafref {
            path "/sp:sonic-pon/sp:PON_OLT_INTF_STATE/sp:PON_OLT_INTF_STATE_LIST/sp:olt-intf-name";
          }
          description
            "References PON_OLT_INTF_STATE_LIST.";
        }
        leaf olt-id {
          type uint16;
          description
            "OLT PON Flood ID (GPON: Multicast XGEM Port ID).";
        }
        leaf-list vlan-tag {
          type string;
          units "S#.C#.C#";
          description
            "NNI Network VLAN tag stack in the format 'S#.C#.C#'.";
        }
      }
    }
    container PON_ONU_STATE {
      description
        "PON_ONU_STATE table in StateDB.";
      config false;
      list PON_ONU_STATE_LIST {
        key "onu-name";
        description
          "List of ONUs.
           StateDB key: PON_ONU_STATE|<onu-name>.";
        leaf onu-name {
          type string;
          description
            "Name identifier to reference this ONU device.";
        }
        leaf timestamp {
          type yang:date-and-time;
          description
            "The last update for this state file";
        }
        leaf onu-id {
          type uint16;
          description
            "ONU ID used on the PON";
        }
        leaf cvid {
          type uint16;
          description
            "VID for service configuration";
        }
        leaf equipment-id {
          type string;
          description
            "Equipment ID as reported by the ONU through G.988 ONU-G.";
        }
        leaf fw-bank-ptr {
          type uint16;
          description
            "Current value of the firmware bank pointer";
        }
        leaf fw-version {
          type string;
          description
            "Current firmware running on the ONU";
        }
        leaf hardware-version {
          type string;
          description
            "Hardware version reported by the ONU.";
        }
        leaf last-provisioning-time {
          type yang:date-and-time;
          description
            "The last time the Controller completed provisioning service for the ONU.";
        }
        leaf mac-address {
          type yang:mac-address;
          description
            "MAC Address for this ONU";
        }
        leaf manufacturer {
          type string;
          description
            "Manufacturer of the ONU";
        }
        leaf model {
          type string;
          description
            "Model name for the ONU";
        }
        leaf online-time {
          type yang:date-and-time;
          description
            "The last time the ONU successfully completed registration with the OLT.";
        }
        leaf realtime-stats {
          type boolean;
          description
            "Enables the ONU state files to show all statistics on every cycle.";
        }
        leaf registration-id {
          type string;
          description
            "ID used for this ONU during PLOAM registration.  This value is sometimes used to authenticate the ONU.";
        }
        leaf alloc-id-omcc {
          type uint16;
          description
            "ONU ID used on the PON";
        }
        leaf host-mac-address {
          type yang:mac-address;
          description
            "MAC Address of the IP Host running on this ONU.";
        }
        leaf laser-bias-current {
          type uint64;
          units "microamp";
          description
            "Current in microAmps. This is reported by the XGS ONU when an Optical Line Supervision Test is performed on the ONU";
        }
        leaf logical-id {
          type string;
          description
            "Logical ID programmed in XGS-PON ONU";
        }
        leaf logical-password {
          type string;
          description
            "Logical Password programmed in XGS-PON ONU";
        }
        leaf omci-txn-correlation-id {
          type uint16;
          description
            "Last OMCI transaction correlation identifier sent by the PON Controller to the ONU.";
        }
        leaf omcc-version {
          type yang:hex-string;
          description
            "This attribute identifies the version of the OMCC protocol being used by the ONU.";
        }
        leaf temperature {
          type decimal64 {
            fraction-digits 3;
          }
          units "degrees celsius";
          description
            "Temperature in degrees Celsius. This is reported by the XGS ONU when an Optical Line Supervision Test is performed on the ONU";
        }
        leaf uptime {
          type uint64;
          units "centiseconds";
          description
            "The time since the ONU module was reset.";
        }
        leaf voltage {
          type decimal64 {
            fraction-digits 3;
          }
          units "millivolt";
          description
            "Power Feed Voltage in milliVolts. This is reported by the XGS ONU when an Optical Line Supervision Test is performed on the ONU";
        }
        leaf registration-id-hex {
          type yang:hex-string;
          description
            "72-character (36-byte) hex-string Registration ID for this ONU.";
        }
        leaf serial-number {
          type string;
          description
            "ONU serial number";
        }
        leaf service-config {
          type string;
          description
            "Current ONU service configuration";
        }
        leaf vendor {
          type string;
          description
            "ONU Vendor. This is normally the chip vendor for the ONU.";
        }
        leaf fw-upgrade-backoff-delay {
          type uint32;
          units "seconds";
          description
            "Time to wait before retransmitting an window.";
        }
        leaf fw-upgrade-backoff-divisor {
          type uint32;
          description
            "Controls the size of the send window during retransmissions. A value of '2' reduces
             the send window size by half for each retransmission. A value of '1' disables the backoff.";
        }
        leaf fw-upgrade-download-format {
          type spt:fw-download-format;
          description
            "The format of OMCI the PON Controller will use to upgrade the ONU, regardless of the OMCC Version it reported.";
        }
        leaf fw-upgrade-end-download-timeout {
          type uint32;
          units "seconds";
          description
            "Time to wait for the final acknowledgement during firmware upgrade. Increase the value
             to allow the ONU additional time to write the firmware image to flash. The PON Controller
             automatically calculates the end-download-timeout when set to a value of zero.
            ";
        }
        leaf fw-upgrade-maximum-retries {
          type uint32;
          description
            "Maximum number of times a window is retransmitted before terminating the ONU
             firmware upgrade and reporting an error.
            ";
        }
        leaf fw-upgrade-maximum-window-size {
          type uint32;
          units "bytes";
          description
            "The maximum send window sized used for transfering firmware to the ONU.";
        }
        leaf fw-upgrade-response-timeout {
          type uint32;
          units "seconds";
          description
            "The time in seconds to wait for an acknowledgement from the ONU during firmware upgrade.";
        }
        leaf ssh-server-state {
          type string;
          description
            "The last reported SSH Server status.";
        }
        leaf registration-disallowed {
          type boolean;
          description
            "When true, the OLT is not allowing the ONU to register because the OLT is not specified in the ONU configuration file.  This value is only true for Disallowed Admin and not for Disallowed Error.";
        }
        leaf bank {
          type uint16;
          description
            "Last firmware bank number (software download ME ID) firmware was downloaded to.";
        }
        leaf current-window {
          type uint8;
          description
            "Current window size for the software download.";
        }
        leaf fx-code {
          type string;
          description
            "OMCI Software Download error code as defined in G.988.";
        }
        leaf file {
          type string;
          description
            "Name of the file to download.";
        }
        leaf negotiated-window {
          type uint8;
          description
            "Initial negotiated window size for the software download.";
        }
        leaf progress {
          type uint8;
          units "Percent complete 0..100";
          description
            "Name of the file to download.";
        }
        leaf retries {
          type uint8;
          description
            "Number of retries during the software download.";
        }
        leaf sent-blocks {
          type uint32;
          description
            "Current number of blocks sent for the software download.";
        }
        leaf status {
          type string;
          description
            "Software download status (Downloading, Success, Failed).";
        }
        leaf total-blocks {
          type uint32;
          description
            "Total number of blocks for the software download.";
        }
        leaf upgrade-duration {
          type string;
          description
            "Length of time in hours, minutes, and seconds for the ONU upgrade to complete.";
        }
        leaf upgrade-time {
          type yang:date-and-time;
          description
            "Timestamp reporting time the ONU was upgraded.";
        }
        leaf aborted {
          type boolean;
          description
            "When true, the ONU firmware upgrade has been aborted.";
        }
        leaf failures {
          type uint32;
          description
            "Failure count from the latest firmware upgrade on this ONU.";
        }
        leaf version-mismatches {
          type uint32;
          description
            "Version mismatch count from the latest firmware upgrade on this ONU.";
        }
      }
    }
    container PON_ONU_STATISTICS_BINNED {
      description
        "PON_ONU_STATISTICS_BINNED table in StateDB.";
      config false;
      list PON_ONU_STATISTICS_BINNED_LIST {
        key "onu-name onu-stats-id";
        description
          "Realtime statistics for the ONU.  These are the values of the statistics after a
           gather to the statistic file.  The ONU statistics vary based on ONU configuration.

           StateDB key: PON_ONU_STATISTICS_BINNED|<onu-name>|<onu-stats-id>.";
        leaf onu-name {
          type leafref {
            path "/sp:sonic-pon/sp:PON_ONU_STATE/sp:PON_ONU_STATE_LIST/sp:onu-name";
          }
          description
            "References PON_ONU_STATE_LIST.";
        }
        leaf olt-pon-rx-optical-level {
          type decimal64 {
            fraction-digits 3;
          }
          units "dBm";
          description
            "Receive optical level.";
        }
        leaf olt-pon-tx-optical-level {
          type decimal64 {
            fraction-digits 3;
          }
          units "dBm";
          description
            "Transmit optical level.";
        }
        leaf olt-pon-rx-deregistrations {
          type uint64;
          description
            "Number of times the ONU has deregistered.";
        }
        leaf olt-pon-rx-registrations {
          type uint64;
          description
            "Number of times the ONU has completed registration.";
        }
        leaf olt-pon-fiber-distance {
          type decimal64 {
            fraction-digits 3;
          }
          units "kilometers";
          description
            "Reports the ONU fiber distance in kilometers.";
        }
        leaf olt-pon-equalization-delay {
          type uint64;
          units "upstream-slots(12.8ns)";
          description
            "Equalization delay assigned by the OLT to an ONU
             to ensure that the ONU's transmissions are aligned on a common
             upstream time reference.";
          reference
            "ITU-T G.9807.1 clause C.13.1";
        }
        leaf olt-pon-round-trip-time {
          type uint64;
          units "TQ(16ns)";
          description
            "Calculated Round Trip Time (RTT) between the OLT and ONU.";
          reference
            "ITU-T G984.3";
        }
        leaf olt-pon-one-way-delay {
          type uint64;
          units "microseconds";
          description
            "One way delay reported for an ONU.";
        }
        leaf olt-pon-rx-acc-fec-bytes {
          type uint64;
          description
            "Receive Accumulated FEC Bytes";
        }
        leaf olt-pon-rx-acc-fec-correct-bytes {
          type uint64;
          description
            "Receive Accumulated FEC Corrected Bytes";
        }
        leaf olt-pon-rx-acc-fec-error-bytes {
          type uint64;
          description
            "Receive Accumulated FEC Errored Bytes";
        }
        leaf olt-pon-rx-pre-fec-ber {
          type string;
          description
            "Receive Pre-FEC Bit Error Rate represented in scientific notation.";
        }
        leaf olt-pon-rx-post-fec-ber {
          type string;
          description
            "Receive Post-FEC Bit Error Rate represented in scientific notation.";
        }
        leaf onu-stats-id {
          type yang:date-and-time;
          description
            "Timestamp identifying the statistics collection period.";
        }
        leaf timestamp {
          type yang:date-and-time;
          description
            "Timestamp when the statistics were collected.";
        }
      }
    }
    container PON_ONU_OLT_SERVICE_STATE {
      description
        "PON_ONU_OLT_SERVICE_STATE table in StateDB.";
      config false;
      list PON_ONU_OLT_SERVICE_STATE_LIST {
        key "onu-name olt-service-id";
        description
          "The OLT provisioned services for this ONU. An entry exists for each service on the OLT for this ONU.
           StateDB key: PON_ONU_OLT_SERVICE_STATE|<onu-name>|<olt-service-id>.";
        leaf onu-name {
          type leafref {
            path "/sp:sonic-pon/sp:PON_ONU_STATE/sp:PON_ONU_STATE_LIST/sp:onu-name";
          }
          description
            "References PON_ONU_STATE_LIST.";
        }
        leaf olt-service-id {
          type uint32;
          description
            "OLT Service Port number.";
        }
        leaf enable {
          type boolean;
          description
            "If the service port is currently enabled or disabled.";
        }
        leaf learning-limit {
          type uint16;
          description
            "Dynamic MAC learning table size limit for this service port. A value of '0' indicates that MAC Learning is disabled for this service.";
        }
        leaf tcont-service-ref {
          type string {
            pattern "none|[0-7]";
          }
          description
            "none - OLT Service Port operates as a TCONT + XGem Port.
             Reference to a OLT Service Port operating in TCONT + XGem mode. A blank
             value indicates this OLT Service Port is operating as TCONT + XGem. Otherwise, a non-empty
             value indicates this OLT Serice Port is operating in XGem-only mode, where the value
             references another OLT Service Port that serves as the TCONT for this XGem Port.
            ";
        }
        leaf unicast-id {
          type uint16;
          description
            "XGEM Port ID for unicast traffic on this service port.";
        }
        leaf upstream-priority-treatment {
          type enumeration {
            enum copy {
              description
                "Copy the priority bits from the inner C-Tag for OLT configurations that add an
                 outer VLAN tag. Copy the priority bits from the original VLAN tag to the new VLAN tag
                 for OLT configurations that translate an outer VLAN tag.
                ";
            }
            enum set {
              description
                "Set the priority to a specific value 0..7 in VLAN tags that are added or
                 translated by the OLT. The priority value is specified by the upstream-priority-value
                 attribute.
                ";
            }
          }
          description
            "Treatment of priority (CoS) bits in VLAN tags added or translated by the OLT for
             frames received upstream from the ONU.";
        }
        leaf upstream-priority-value {
          type uint8;
          description
            "VLAN tag priority value to insert in frames when the upstream-priority-treatment
             attribute is 'set'.
            ";
        }
        leaf sla-downstream-guaranteed-rate {
          type uint32;
          units "kbps";
          description
            "Guaranteed (high priority) rate in kbps.";
        }
        leaf sla-downstream-guaranteed-maximum-burst {
          type uint32;
          units "kBytes";
          description
            "Maximum burst size in Kilobytes. The guaranteed rate is enforced at this burst size.";
        }
        leaf sla-downstream-best-effort-rate {
          type uint32;
          units "kbps";
          description
            "Best Effort (low priority) rate in kbps.";
        }
        leaf sla-downstream-best-effort-maximum-burst {
          type uint32;
          units "kBytes";
          description
            "Maximum burst size in Kilobytes. The best effort rate is enforced at this burst size.";
        }
        leaf sla-upstream-fixed-rate {
          type uint32;
          units "kbps";
          description
            "Fixed grant rate in kbps. This is an unsolicited grant by the DBA regardless of need.";
        }
        leaf sla-upstream-guaranteed-rate {
          type uint32;
          units "kbps";
          description
            "Guaranteed (high priority) rate in kbps.";
        }
        leaf sla-upstream-guaranteed-maximum-burst {
          type uint32;
          units "kBytes";
          description
            "Maximum burst size in Kilobytes. The guaranteed rate is enforced at this burst size.";
        }
        leaf sla-upstream-priority {
          type uint8;
          description
            "Priority level for the guaranteed portion of the SLA.";
        }
        leaf sla-upstream-best-effort-rate {
          type uint32;
          units "kbps";
          description
            "Best Effort (low priority) rate in kbps.";
        }
        leaf sla-upstream-best-effort-maximum-burst {
          type uint32;
          units "kBytes";
          description
            "Maximum burst size in Kilobytes. The best effort rate is enforced at this burst size.";
        }
        leaf sla-upstream-best-effort-priority {
          type uint8;
          description
            "Priority level for the Best Effort portion of the SLA.";
        }
        leaf downstream-qos-map {
          type string;
          description
            "Name of the downstream QoS map applied to this OLT service port.";
        }
        ordered-by system;
      }
    }
    container PON_ONU_OLT_SERVICE_DOWNSTREAM_QOS_MAP_STATE {
      description
        "PON_ONU_OLT_SERVICE_DOWNSTREAM_QOS_MAP_STATE table in StateDB.";
      config false;
      list PON_ONU_OLT_SERVICE_DOWNSTREAM_QOS_MAP_STATE_LIST {
        key "onu-name olt-service-id";
        description
          "Downstream QoS Map
           StateDB key: PON_ONU_OLT_SERVICE_DOWNSTREAM_QOS_MAP_STATE|<onu-name>|<olt-service-id>.";
        leaf onu-name {
          type leafref {
            path "/sp:sonic-pon/sp:PON_ONU_STATE/sp:PON_ONU_STATE_LIST/sp:onu-name";
          }
          description
            "References PON_ONU_STATE_LIST.";
        }
        leaf olt-service-id {
          type leafref {
            path "/sp:sonic-pon/sp:PON_ONU_OLT_SERVICE_STATE/sp:PON_ONU_OLT_SERVICE_STATE_LIST/sp:olt-service-id";
          }
          description
            "References PON_ONU_OLT_SERVICE_STATE_LIST.";
        }
        leaf type {
          type string;
          description
            "Type of Downstream QoS Map.";
        }
      }
    }
    container PON_ONU_OLT_SERVICE_DOWNSTREAM_QOS_MAP_MAP_STATE {
      description
        "PON_ONU_OLT_SERVICE_DOWNSTREAM_QOS_MAP_MAP_STATE table in StateDB.";
      config false;
      list PON_ONU_OLT_SERVICE_DOWNSTREAM_QOS_MAP_MAP_STATE_LIST {
        key "onu-name olt-service-id priority";
        description
          "Mapping entry that classifies VLAN CoS bit values to a destination GPON XGEM Port (OLT-Service) offset.

           StateDB key: PON_ONU_OLT_SERVICE_DOWNSTREAM_QOS_MAP_MAP_STATE|<onu-name>|<olt-service-id>|<priority>.";
        leaf onu-name {
          type leafref {
            path "/sp:sonic-pon/sp:PON_ONU_OLT_SERVICE_DOWNSTREAM_QOS_MAP_STATE/sp:PON_ONU_OLT_SERVICE_DOWNSTREAM_QOS_MAP_STATE_LIST/sp:onu-name";
          }
          description
            "References PON_ONU_OLT_SERVICE_DOWNSTREAM_QOS_MAP_STATE_LIST.";
        }
        leaf olt-service-id {
          type leafref {
            path "/sp:sonic-pon/sp:PON_ONU_OLT_SERVICE_DOWNSTREAM_QOS_MAP_STATE/sp:PON_ONU_OLT_SERVICE_DOWNSTREAM_QOS_MAP_STATE_LIST/sp:olt-service-id";
          }
          description
            "References PON_ONU_OLT_SERVICE_DOWNSTREAM_QOS_MAP_STATE_LIST.";
        }
        leaf priority {
          type uint8;
          description
            "Priority (CoS bit) value.";
        }
        leaf olt-service-offset {
          type uint8;
          description
            "Destination GPON XGEM Port offset that the start/end CoS values are classified to.";
        }
      }
    }
    container PON_ONU_OLT_SERVICE_NETWORK_STATE {
      description
        "PON_ONU_OLT_SERVICE_NETWORK_STATE table in StateDB.";
      config false;
      list PON_ONU_OLT_SERVICE_NETWORK_STATE_LIST {
        key "onu-name olt-service-id vlan-id";
        description
          "List of C-VLAN IDs through the service flow List of PON VLAN network through service flow
           StateDB key: PON_ONU_OLT_SERVICE_NETWORK_STATE|<onu-name>|<olt-service-id>|<vlan-id>.";
        leaf onu-name {
          type leafref {
            path "/sp:sonic-pon/sp:PON_ONU_STATE/sp:PON_ONU_STATE_LIST/sp:onu-name";
          }
          description
            "References PON_ONU_STATE_LIST.";
        }
        leaf olt-service-id {
          type leafref {
            path "/sp:sonic-pon/sp:PON_ONU_OLT_SERVICE_STATE/sp:PON_ONU_OLT_SERVICE_STATE_LIST/sp:olt-service-id";
          }
          description
            "References PON_ONU_OLT_SERVICE_STATE_LIST.";
        }
        leaf network-id {
          type uint16;
          description
            "Index for this entry.";
        }
        leaf vlan-id {
          type uint16 {
            range "0..4095";
          }
          description
            "VLAN ID.";
        }
        ordered-by system;
      }
    }
    container PON_ONU_UNI_STATE {
      description
        "PON_ONU_UNI_STATE table in StateDB.";
      config false;
      list PON_ONU_UNI_STATE_LIST {
        key "onu-name port-id";
        description
          "Status of the UNI ports on the ONU.
           StateDB key: PON_ONU_UNI_STATE|<onu-name>|<port-id>.";
        leaf onu-name {
          type leafref {
            path "/sp:sonic-pon/sp:PON_ONU_STATE/sp:PON_ONU_STATE_LIST/sp:onu-name";
          }
          description
            "References PON_ONU_STATE_LIST.";
        }
        leaf port-id {
          type string {
            pattern 'UNI-ETH\s[1-9][0-9]?';
          }
          description
            "Identifier for this UNI port.";
        }
        leaf duplex {
          type string;
          description
            "Sets the duplex for the Ethernet port";
        }
        leaf enable {
          type boolean;
          description
            "Current enable state of the Ethernet port";
        }
        leaf managed-entity-id {
          type uint16;
          description
            "OMCI Managed Entity Identifier for the UNI";
        }
        leaf max-frame-size {
          type uint32;
          description
            "Maximum Frame size limit on UNI receive";
        }
        leaf poe {
          type boolean;
          description
            "Power over Ethernet (PoE) status for the UNI port.";
          reference
            "ITU-T G.988 clause 9.5.1 Physical path termination point Ethernet UNI, Power control";
        }
        leaf speed {
          type string;
          description
            "Set the speed of the Ethernet port";
        }
        leaf state {
          type string;
          description
            "The link status of the UNI Ethernet port";
        }
      }
    }
    container PON_ONU_FW_BANK_VERSION_STATE {
      description
        "PON_ONU_FW_BANK_VERSION_STATE table in StateDB.";
      config false;
      list PON_ONU_FW_BANK_VERSION_STATE_LIST {
        key "onu-name bank-id";
        description
          "Current firmware contents of ONU banks
           StateDB key: PON_ONU_FW_BANK_VERSION_STATE|<onu-name>|<bank-id>.";
        leaf onu-name {
          type leafref {
            path "/sp:sonic-pon/sp:PON_ONU_STATE/sp:PON_ONU_STATE_LIST/sp:onu-name";
          }
          description
            "References PON_ONU_STATE_LIST.";
        }
        leaf bank-id {
          type uint8;
          description
            "Index for this entry.";
        }
        leaf version {
          type string;
          description
            "Firmware version.";
        }
        ordered-by system;
      }
    }
    container PON_ONU_STATISTICS_BINNED_OLT_PON {
      description
        "PON_ONU_STATISTICS_BINNED_OLT_PON table in StateDB.";
      config false;
      list PON_ONU_STATISTICS_BINNED_OLT_PON_LIST {
        key "onu-name onu-stats-id";
        description
          "PON statistics for this ONU as represented on the OLT.
           StateDB key: PON_ONU_STATISTICS_BINNED_OLT_PON|<onu-name>|<onu-stats-id>.";
        leaf onu-name {
          type leafref {
            path "/sp:sonic-pon/sp:PON_ONU_STATE/sp:PON_ONU_STATE_LIST/sp:onu-name";
          }
          description
            "References PON_ONU_STATE_LIST.";
        }
        leaf onu-stats-id {
          type leafref {
            path "/sp:sonic-pon/sp:PON_ONU_STATISTICS_BINNED/sp:PON_ONU_STATISTICS_BINNED_LIST/sp:onu-stats-id";
          }
          description
            "References PON_ONU_STATISTICS_BINNED_LIST.";
        }
        leaf rx-optical-level {
          type decimal64 {
            fraction-digits 3;
          }
          units "dBm";
          description
            "Receive optical level.";
        }
        leaf tx-optical-level {
          type decimal64 {
            fraction-digits 3;
          }
          units "dBm";
          description
            "Transmit optical level.";
        }
        leaf rx-deregistrations {
          type uint64;
          description
            "Number of times the ONU has deregistered.";
        }
        leaf rx-registrations {
          type uint64;
          description
            "Number of times the ONU has completed registration.";
        }
        leaf fiber-distance {
          type decimal64 {
            fraction-digits 3;
          }
          units "kilometers";
          description
            "Reports the ONU fiber distance in kilometers.";
        }
        leaf equalization-delay {
          type uint64;
          units "upstream-slots(12.8ns)";
          description
            "Equalization delay assigned by the OLT to an ONU
             to ensure that the ONU's transmissions are aligned on a common
             upstream time reference.";
          reference
            "ITU-T G.9807.1 clause C.13.1";
        }
        leaf round-trip-time {
          type uint64;
          units "TQ(16ns)";
          description
            "Calculated Route Trip Time (RTT) between the OLT and ONU.";
          reference
            "IEEE 802.3av section 77.2.1.1";
        }
        leaf one-way-delay {
          type uint64;
          units "microseconds";
          description
            "One way delay reported for an ONU.";
        }
      }
    }
    container PON_ONU_STATISTICS_BINNED_OLT_PON_OMCC {
      description
        "PON_ONU_STATISTICS_BINNED_OLT_PON_OMCC table in StateDB.";
      config false;
      list PON_ONU_STATISTICS_BINNED_OLT_PON_OMCC_LIST {
        key "onu-name onu-stats-id";
        description
          "GPON: OMCI channel statistics for this ONU as represented on the OLT.
           StateDB key: PON_ONU_STATISTICS_BINNED_OLT_PON_OMCC|<onu-name>|<onu-stats-id>.";
        leaf onu-name {
          type leafref {
            path "/sp:sonic-pon/sp:PON_ONU_STATE/sp:PON_ONU_STATE_LIST/sp:onu-name";
          }
          description
            "References PON_ONU_STATE_LIST.";
        }
        leaf onu-stats-id {
          type leafref {
            path "/sp:sonic-pon/sp:PON_ONU_STATISTICS_BINNED/sp:PON_ONU_STATISTICS_BINNED_LIST/sp:onu-stats-id";
          }
          description
            "References PON_ONU_STATISTICS_BINNED_LIST.";
        }
        leaf bad-key-exchanges {
          type uint64;
          description
            "Bad Key Exchanges";
        }
        leaf good-key-exchanges {
          type uint64;
          description
            "Good Key Exchanges";
        }
        leaf omci-oam-requests {
          type uint64;
          description
            "OMCI/OAM Requests";
        }
        leaf omci-oam-resp-time-avg {
          type uint64;
          units "microseconds";
          description
            "OMCI/OAM Resp Time Avg";
        }
        leaf omci-oam-resp-time-max {
          type uint64;
          units "microseconds";
          description
            "OMCI/OAM Resp Time Max";
        }
        leaf omci-oam-resp-time-min {
          type uint64;
          units "microseconds";
          description
            "OMCI/OAM Resp Time Min";
        }
        leaf omci-oam-responses {
          type uint64;
          description
            "OMCI/OAM Responses";
        }
        leaf omci-oam-time-to-send-avg {
          type uint64;
          units "microseconds";
          description
            "OMCI/OAM Time to Send Avg";
        }
        leaf omci-oam-time-to-send-max {
          type uint64;
          units "microseconds";
          description
            "OMCI/OAM Time to Send Max";
        }
        leaf omci-oam-time-to-send-min {
          type uint64;
          units "microseconds";
          description
            "OMCI/OAM Time to Send Min";
        }
        leaf omci-oam-timeouts {
          type uint64;
          description
            "OMCI/OAM Timeouts";
        }
        leaf ploam-timeouts {
          type uint64;
          description
            "PLOAM Timeouts";
        }
        leaf rx-all-bandwidth-reqs {
          type uint64;
          description
            "Receive All Bandwidth Reqs";
        }
        leaf rx-bad-icv-drops {
          type uint64;
          description
            "Receive Bad ICV Drops";
        }
        leaf rx-bandwidth-reqs {
          type uint64;
          description
            "Receive Bandwidth Reqs";
        }
        leaf rx-crc32-drops {
          type uint64;
          description
            "Receive CRC32 Drops";
        }
        leaf rx-crc8-errors {
          type uint64;
          description
            "Receive CRC8 Errors";
        }
        leaf rx-control-octets {
          type uint64;
          description
            "Receive Control Octets";
        }
        leaf rx-empty-slots {
          type uint64;
          description
            "Receive Empty Slots";
        }
        leaf rx-encrypted-octets {
          type uint64;
          description
            "Receive Encrypted Octets";
        }
        leaf rx-encrypted-segments {
          type uint64;
          description
            "Receive Encrypted Segments";
        }
        leaf rx-errored-bip-bits {
          type uint64;
          description
            "Receive Errored BIP Bits";
        }
        leaf rx-errored-bip-blocks {
          type uint64;
          description
            "Receive Errored BIP Blocks";
        }
        leaf rx-fec-corrected-blocks {
          type uint64;
          description
            "Receive FEC Corrected Blocks";
        }
        leaf rx-fec-corrections {
          type uint64;
          description
            "Receive FEC Corrections";
        }
        leaf rx-fec-good-blocks {
          type uint64;
          description
            "Receive FEC Good Blocks";
        }
        leaf rx-fec-uncorrectable-blocks {
          type uint64;
          description
            "Receive FEC Uncorrectable Blocks";
        }
        leaf rx-filtered-frames {
          type uint64;
          description
            "Receive Filtered Frames";
        }
        leaf rx-frames-1024_1518 {
          type uint64;
          description
            "Receive Frames 1024-1518";
        }
        leaf rx-frames-128_255 {
          type uint64;
          description
            "Receive Frames 128-255";
        }
        leaf rx-frames-1519_plus {
          type uint64;
          description
            "Receive Frames 1519-Plus";
        }
        leaf rx-frames-256_511 {
          type uint64;
          description
            "Receive Frames 256-511";
        }
        leaf rx-frames-512_1023 {
          type uint64;
          description
            "Receive Frames 512-1023";
        }
        leaf rx-frames-64 {
          type uint64;
          description
            "Receive Frames 64";
        }
        leaf rx-frames-65_127 {
          type uint64;
          description
            "Receive Frames 65-127";
        }
        leaf rx-frames-green {
          type uint64;
          description
            "Receive Frames Green";
        }
        leaf rx-good-bip-blocks {
          type uint64;
          description
            "Receive Good BIP Blocks";
        }
        leaf rx-hec-errors {
          type uint64;
          description
            "Receive HEC Errors";
        }
        leaf rx-idle-octets {
          type uint64;
          description
            "Receive Idle Octets";
        }
        leaf rx-key-mismatch-octets {
          type uint64;
          description
            "Receive Key Mismatch Octets";
        }
        leaf rx-mpcp-ploam {
          type uint64;
          description
            "Receive MPCP/PLOAM";
        }
        leaf rx-multi-broadcast-octets {
          type uint64;
          description
            "Receive Multi/Broadcast Octets";
        }
        leaf rx-oam {
          type uint64;
          description
            "Receive OAM";
        }
        leaf rx-overflow-drops {
          type uint64;
          description
            "Receive Overflow Drops";
        }
        leaf rx-overflow-octets {
          type uint64;
          description
            "Receive Overflow Octets";
        }
        leaf rx-plain-octets {
          type uint64;
          description
            "Receive Plain Octets";
        }
        leaf rx-plain-segments {
          type uint64;
          description
            "Receive Plain Segments";
        }
        leaf rx-ploam-mic-errors {
          type uint64;
          description
            "Receive PLOAM MIC Errors";
        }
        leaf rx-rate-bps {
          type uint64;
          description
            "Receive Rate bps";
        }
        leaf rx-security-drop-octets {
          type uint64;
          description
            "Receive Security Drop Octets";
        }
        leaf rx-too-long-drops {
          type uint64;
          description
            "Receive Too Long Drops";
        }
        leaf rx-too-short-drops {
          type uint64;
          description
            "Receive Too Short Drops";
        }
        leaf rx-total-octets {
          type uint64;
          description
            "Receive Total Octets";
        }
        leaf rx-unicast-octets {
          type uint64;
          description
            "Receive Unicast Octets";
        }
        leaf tx-bandwidth-reqs {
          type uint64;
          description
            "Transmit Bandwidth Reqs";
        }
        leaf tx-control-octets {
          type uint64;
          description
            "Transmit Control Octets";
        }
        leaf tx-encrypted-octets {
          type uint64;
          description
            "Transmit Encrypted Octets";
        }
        leaf tx-encrypted-segments {
          type uint64;
          description
            "Transmit Encrypted Segments";
        }
        leaf tx-frames-1024_1518 {
          type uint64;
          description
            "Transmit Frames 1024-1518";
        }
        leaf tx-frames-128_255 {
          type uint64;
          description
            "Transmit Frames 128-255";
        }
        leaf tx-frames-1519_plus {
          type uint64;
          description
            "Transmit Frames 1519-Plus";
        }
        leaf tx-frames-256_511 {
          type uint64;
          description
            "Transmit Frames 256-511";
        }
        leaf tx-frames-512_1023 {
          type uint64;
          description
            "Transmit Frames 512-1023";
        }
        leaf tx-frames-64 {
          type uint64;
          description
            "Transmit Frames 64";
        }
        leaf tx-frames-65_127 {
          type uint64;
          description
            "Transmit Frames 65-127";
        }
        leaf tx-frames-broadcast {
          type uint64;
          description
            "Transmit Frames Broadcast";
        }
        leaf tx-frames-green {
          type uint64;
          description
            "Transmit Frames Green";
        }
        leaf tx-frames-multicast {
          type uint64;
          description
            "Transmit Frames Multicast";
        }
        leaf tx-frames-unicast {
          type uint64;
          description
            "Transmit Frames Unicast";
        }
        leaf tx-grant-ups-tq {
          type uint64;
          description
            "Transmit Grant UPS Tq";
        }
        leaf tx-mpcp-ploam {
          type uint64;
          description
            "Transmit MPCP/PLOAM";
        }
        leaf tx-multi-broadcast-octets {
          type uint64;
          description
            "Transmit Multi/Broadcast Octets";
        }
        leaf tx-oam {
          type uint64;
          description
            "Transmit OAM";
        }
        leaf tx-plain-octets {
          type uint64;
          description
            "Transmit Plain Octets";
        }
        leaf tx-plain-segments {
          type uint64;
          description
            "Transmit Plain Segments";
        }
        leaf tx-ploam-ds-ranging-time {
          type uint64;
          description
            "Transmit PLOAM DS Ranging Time";
        }
        leaf tx-total-octets {
          type uint64;
          description
            "Transmit Total Octets";
        }
        leaf tx-unicast-octets {
          type uint64;
          description
            "Transmit Unicast Octets";
        }
        leaf tx-upstream-slots {
          type uint64;
          description
            "Transmit Upstream Slots";
        }
      }
    }
    container PON_ONU_STATISTICS_BINNED_ONU_PON {
      description
        "PON_ONU_STATISTICS_BINNED_ONU_PON table in StateDB.";
      config false;
      list PON_ONU_STATISTICS_BINNED_ONU_PON_LIST {
        key "onu-name onu-stats-id";
        description
          "PON statistics reported by ONU.
           StateDB key: PON_ONU_STATISTICS_BINNED_ONU_PON|<onu-name>|<onu-stats-id>.";
        leaf onu-name {
          type leafref {
            path "/sp:sonic-pon/sp:PON_ONU_STATE/sp:PON_ONU_STATE_LIST/sp:onu-name";
          }
          description
            "References PON_ONU_STATE_LIST.";
        }
        leaf onu-stats-id {
          type leafref {
            path "/sp:sonic-pon/sp:PON_ONU_STATISTICS_BINNED/sp:PON_ONU_STATISTICS_BINNED_LIST/sp:onu-stats-id";
          }
          description
            "References PON_ONU_STATISTICS_BINNED_LIST.";
        }
        leaf rx-optical-level {
          type decimal64 {
            fraction-digits 3;
          }
          units "dBm";
          description
            "Receive Optical Level";
        }
        leaf tx-optical-level {
          type decimal64 {
            fraction-digits 3;
          }
          units "dBm";
          description
            "Transmit Optical Level";
        }
      }
    }
    container PON_ONU_STATISTICS_BINNED_OLT_PON_SERVICE {
      description
        "PON_ONU_STATISTICS_BINNED_OLT_PON_SERVICE table in StateDB.";
      config false;
      list PON_ONU_STATISTICS_BINNED_OLT_PON_SERVICE_LIST {
        key "onu-name onu-stats-id service-port-id";
        description
          "OLT-Service Port statistics for this ONU as represented on the OLT.
           StateDB key: PON_ONU_STATISTICS_BINNED_OLT_PON_SERVICE|<onu-name>|<onu-stats-id>|<service-port-id>.";
        leaf onu-name {
          type leafref {
            path "/sp:sonic-pon/sp:PON_ONU_STATE/sp:PON_ONU_STATE_LIST/sp:onu-name";
          }
          description
            "References PON_ONU_STATE_LIST.";
        }
        leaf onu-stats-id {
          type leafref {
            path "/sp:sonic-pon/sp:PON_ONU_STATISTICS_BINNED/sp:PON_ONU_STATISTICS_BINNED_LIST/sp:onu-stats-id";
          }
          description
            "References PON_ONU_STATISTICS_BINNED_LIST.";
        }
        leaf service-port-id {
          type uint8;
          description
            "OLT-Service Port number.";
        }
        leaf bad-key-exchanges {
          type uint64;
          description
            "Bad Key Exchanges";
        }
        leaf enable-count {
          type uint64;
          description
            "Number of times the OLT-Service was activated.";
        }
        leaf good-key-exchanges {
          type uint64;
          description
            "Good Key Exchanges";
        }
        leaf omci-oam-requests {
          type uint64;
          description
            "OMCI/OAM Requests";
        }
        leaf omci-oam-resp-time-avg {
          type uint64;
          units "microseconds";
          description
            "OMCI/OAM Resp Time Avg";
        }
        leaf omci-oam-resp-time-max {
          type uint64;
          units "microseconds";
          description
            "OMCI/OAM Resp Time Max";
        }
        leaf omci-oam-resp-time-min {
          type uint64;
          units "microseconds";
          description
            "OMCI/OAM Resp Time Min";
        }
        leaf omci-oam-responses {
          type uint64;
          description
            "OMCI/OAM Responses";
        }
        leaf omci-oam-time-to-send-avg {
          type uint64;
          units "microseconds";
          description
            "OMCI/OAM Time to Send Avg";
        }
        leaf omci-oam-time-to-send-max {
          type uint64;
          units "microseconds";
          description
            "OMCI/OAM Time to Send Max";
        }
        leaf omci-oam-time-to-send-min {
          type uint64;
          units "microseconds";
          description
            "OMCI/OAM Time to Send Min";
        }
        leaf omci-oam-timeouts {
          type uint64;
          description
            "OMCI/OAM Timeouts";
        }
        leaf ploam-timeouts {
          type uint64;
          description
            "PLOAM Timeouts";
        }
        leaf rx-all-bandwidth-reqs {
          type uint64;
          description
            "Receive All Bandwidth Reqs";
        }
        leaf rx-bw-best-effort-sla-util {
          type uint64;
          description
            "Receive BW Best Effort SLA Util";
        }
        leaf rx-bw-best-effort-sla-bps {
          type uint64;
          description
            "Receive BW Best Effort SLA bps";
        }
        leaf rx-bw-fixed-sla-util {
          type uint64;
          description
            "Receive BW Fixed SLA Util";
        }
        leaf rx-bw-fixed-sla-bps {
          type uint64;
          description
            "Receive BW Fixed SLA bps";
        }
        leaf rx-bw-guaranteed-sla-util {
          type uint64;
          description
            "Receive BW Guaranteed SLA Util";
        }
        leaf rx-bw-guaranteed-sla-bps {
          type uint64;
          description
            "Receive BW Guaranteed SLA bps";
        }
        leaf rx-bw-total-sla-util {
          type uint64;
          description
            "Receive BW Total SLA Util";
        }
        leaf rx-bw-total-sla-bps {
          type uint64;
          description
            "Receive BW Total SLA bps";
        }
        leaf rx-bad-icv-drops {
          type uint64;
          description
            "Receive Bad ICV Drops";
        }
        leaf rx-bandwidth-reqs {
          type uint64;
          description
            "Receive Bandwidth Reqs";
        }
        leaf rx-crc32-drops {
          type uint64;
          description
            "Receive CRC32 Drops";
        }
        leaf rx-crc8-errors {
          type uint64;
          description
            "Receive CRC8 Errors";
        }
        leaf rx-control-octets {
          type uint64;
          description
            "Receive Control Octets";
        }
        leaf rx-empty-slots {
          type uint64;
          description
            "Receive Empty Slots";
        }
        leaf rx-encrypted-frames {
          type uint64;
          description
            "Receive Encrypted Frames";
        }
        leaf rx-encrypted-octets {
          type uint64;
          description
            "Receive Encrypted Octets";
        }
        leaf rx-encrypted-segments {
          type uint64;
          description
            "Receive Encrypted Segments";
        }
        leaf rx-errored-bip-bits {
          type uint64;
          description
            "Receive Errored BIP Bits";
        }
        leaf rx-errored-bip-blocks {
          type uint64;
          description
            "Receive Errored BIP Blocks";
        }
        leaf rx-fec-corrected-blocks {
          type uint64;
          description
            "Receive FEC Corrected Blocks";
        }
        leaf rx-fec-corrections {
          type uint64;
          description
            "Receive FEC Corrections";
        }
        leaf rx-fec-good-blocks {
          type uint64;
          description
            "Receive FEC Good Blocks";
        }
        leaf rx-fec-uncorrectable-blocks {
          type uint64;
          description
            "Receive FEC Uncorrectable Blocks";
        }
        leaf rx-filtered-frames {
          type uint64;
          description
            "Receive Filtered Frames";
        }
        leaf rx-frames-1024_1518 {
          type uint64;
          description
            "Receive Frames 1024-1518";
        }
        leaf rx-frames-128_255 {
          type uint64;
          description
            "Receive Frames 128-255";
        }
        leaf rx-frames-1519_plus {
          type uint64;
          description
            "Receive Frames 1519-Plus";
        }
        leaf rx-frames-256_511 {
          type uint64;
          description
            "Receive Frames 256-511";
        }
        leaf rx-frames-512_1023 {
          type uint64;
          description
            "Receive Frames 512-1023";
        }
        leaf rx-frames-64 {
          type uint64;
          description
            "Receive Frames 64";
        }
        leaf rx-frames-65_127 {
          type uint64;
          description
            "Receive Frames 65-127";
        }
        leaf rx-frames-green {
          type uint64;
          description
            "Receive Frames Green";
        }
        leaf rx-good-bip-blocks {
          type uint64;
          description
            "Receive Good BIP Blocks";
        }
        leaf rx-hec-errors {
          type uint64;
          description
            "Receive HEC Errors";
        }
        leaf rx-idle-octets {
          type uint64;
          description
            "Receive Idle Octets";
        }
        leaf rx-key-mismatch-octets {
          type uint64;
          description
            "Receive Key Mismatch Octets";
        }
        leaf rx-mpcp-ploam {
          type uint64;
          description
            "Receive MPCP/PLOAM";
        }
        leaf rx-multi-broadcast-octets {
          type uint64;
          description
            "Receive Multi/Broadcast Octets";
        }
        leaf rx-overflow-drops {
          type uint64;
          description
            "Receive Overflow Drops";
        }
        leaf rx-overflow-octets {
          type uint64;
          description
            "Receive Overflow Octets";
        }
        leaf rx-plain-frames {
          type uint64;
          description
            "Receive Plain Frames";
        }
        leaf rx-plain-octets {
          type uint64;
          description
            "Receive Plain Octets";
        }
        leaf rx-plain-segments {
          type uint64;
          description
            "Receive Plain Segments";
        }
        leaf rx-ploam-mic-errors {
          type uint64;
          description
            "Receive PLOAM MIC Errors";
        }
        leaf rx-rate-bps {
          type uint64;
          description
            "Receive Rate bps";
        }
        leaf rx-security-drop-octets {
          type uint64;
          description
            "Receive Security Drop Octets";
        }
        leaf rx-too-long-drops {
          type uint64;
          description
            "Receive Too Long Drops";
        }
        leaf rx-too-short-drops {
          type uint64;
          description
            "Receive Too Short Drops";
        }
        leaf rx-total-octets {
          type uint64;
          description
            "Receive Total Octets";
        }
        leaf rx-unicast-octets {
          type uint64;
          description
            "Receive Unicast Octets";
        }
        leaf tx-bw-best-effort-sla-util {
          type uint64;
          description
            "Transmit BW Best Effort SLA Util";
        }
        leaf tx-bw-best-effort-sla-bps {
          type uint64;
          description
            "Transmit BW Best Effort SLA bps";
        }
        leaf tx-bw-guaranteed-sla-util {
          type uint64;
          description
            "Transmit BW Guaranteed SLA Util";
        }
        leaf tx-bw-guaranteed-sla-bps {
          type uint64;
          description
            "Transmit BW Guaranteed SLA bps";
        }
        leaf tx-bw-total-sla-util {
          type uint64;
          description
            "Transmit BW Total SLA Util";
        }
        leaf tx-bw-total-sla-bps {
          type uint64;
          description
            "Transmit BW Total SLA bps";
        }
        leaf tx-bandwidth-reqs {
          type uint64;
          description
            "Transmit Bandwidth Reqs";
        }
        leaf tx-control-octets {
          type uint64;
          description
            "Transmit Control Octets";
        }
        leaf tx-encrypted-frames {
          type uint64;
          description
            "Transmit Encrypted Frames";
        }
        leaf tx-encrypted-octets {
          type uint64;
          description
            "Transmit Encrypted Octets";
        }
        leaf tx-encrypted-segments {
          type uint64;
          description
            "Transmit Encrypted Segments";
        }
        leaf tx-frames-1024_1518 {
          type uint64;
          description
            "Transmit Frames 1024-1518";
        }
        leaf tx-frames-128_255 {
          type uint64;
          description
            "Transmit Frames 128-255";
        }
        leaf tx-frames-1519_plus {
          type uint64;
          description
            "Transmit Frames 1519-Plus";
        }
        leaf tx-frames-256_511 {
          type uint64;
          description
            "Transmit Frames 256-511";
        }
        leaf tx-frames-512_1023 {
          type uint64;
          description
            "Transmit Frames 512-1023";
        }
        leaf tx-frames-64 {
          type uint64;
          description
            "Transmit Frames 64";
        }
        leaf tx-frames-65_127 {
          type uint64;
          description
            "Transmit Frames 65-127";
        }
        leaf tx-frames-broadcast {
          type uint64;
          description
            "Transmit Frames Broadcast";
        }
        leaf tx-frames-green {
          type uint64;
          description
            "Transmit Frames Green";
        }
        leaf tx-frames-multicast {
          type uint64;
          description
            "Transmit Frames Multicast";
        }
        leaf tx-frames-unicast {
          type uint64;
          description
            "Transmit Frames Unicast";
        }
        leaf tx-mpcp-ploam {
          type uint64;
          description
            "Transmit MPCP/PLOAM";
        }
        leaf tx-multi-broadcast-octets {
          type uint64;
          description
            "Transmit Multi/Broadcast Octets";
        }
        leaf tx-plain-frames {
          type uint64;
          description
            "Transmit Plain Frames";
        }
        leaf tx-plain-octets {
          type uint64;
          description
            "Transmit Plain Octets";
        }
        leaf tx-plain-segments {
          type uint64;
          description
            "Transmit Plain Segments";
        }
        leaf tx-ploam-ds-ranging-time {
          type uint64;
          description
            "Transmit PLOAM DS Ranging Time";
        }
        leaf tx-rate-bps {
          type uint64;
          description
            "Transmit Rate bps";
        }
        leaf tx-total-octets {
          type uint64;
          description
            "Transmit Total Octets";
        }
        leaf tx-unicast-octets {
          type uint64;
          description
            "Transmit Unicast Octets";
        }
        leaf tx-upstream-slots {
          type uint64;
          description
            "Transmit Upstream Slots";
        }
      }
    }
    container PON_ONU_STATISTICS_BINNED_ONU_FEC_PM {
      description
        "PON_ONU_STATISTICS_BINNED_ONU_FEC_PM table in StateDB.";
      config false;
      list PON_ONU_STATISTICS_BINNED_ONU_FEC_PM_LIST {
        key "onu-name onu-stats-id me-id";
        description
          "GPON: FEC statistics reported by ONU through OMCI.
           StateDB key: PON_ONU_STATISTICS_BINNED_ONU_FEC_PM|<onu-name>|<onu-stats-id>|<me-id>.";
        leaf onu-name {
          type leafref {
            path "/sp:sonic-pon/sp:PON_ONU_STATE/sp:PON_ONU_STATE_LIST/sp:onu-name";
          }
          description
            "References PON_ONU_STATE_LIST.";
        }
        leaf onu-stats-id {
          type leafref {
            path "/sp:sonic-pon/sp:PON_ONU_STATISTICS_BINNED/sp:PON_ONU_STATISTICS_BINNED_LIST/sp:onu-stats-id";
          }
          description
            "References PON_ONU_STATISTICS_BINNED_LIST.";
        }
        leaf me-id {
          type uint16;
          description
            "Performance management ME ID.";
        }
        leaf corrected-bytes {
          type uint64;
          description
            "corrected bytes";
        }
        leaf corrected-code-words {
          type uint64;
          description
            "corrected code words";
        }
        leaf fec-seconds {
          type uint64;
          description
            "fec seconds";
        }
        leaf interval-end-time {
          type uint64;
          description
            "interval end time";
        }
        leaf threshold-data-1-2-id {
          type omci-types:omci-uint16;
          description
            "threshold data 1/2 id";
        }
        leaf total-code-words {
          type uint64;
          description
            "total code words";
        }
        leaf uncorrectable-code-words {
          type uint64;
          description
            "uncorrectable code words";
        }
      }
    }
    container PON_ONU_STATISTICS_BINNED_ONU_ETHERNET_FRAME_EXTENDED_PM {
      description
        "PON_ONU_STATISTICS_BINNED_ONU_ETHERNET_FRAME_EXTENDED_PM table in StateDB.";
      config false;
      list PON_ONU_STATISTICS_BINNED_ONU_ETHERNET_FRAME_EXTENDED_PM_LIST {
        key "onu-name onu-stats-id me-id";
        description
          "GPON: MAC Bridge Port statistics reported by ONU through OMCI.
           StateDB key: PON_ONU_STATISTICS_BINNED_ONU_ETHERNET_FRAME_EXTENDED_PM|<onu-name>|<onu-stats-id>|<me-id>.";
        leaf onu-name {
          type leafref {
            path "/sp:sonic-pon/sp:PON_ONU_STATE/sp:PON_ONU_STATE_LIST/sp:onu-name";
          }
          description
            "References PON_ONU_STATE_LIST.";
        }
        leaf onu-stats-id {
          type leafref {
            path "/sp:sonic-pon/sp:PON_ONU_STATISTICS_BINNED/sp:PON_ONU_STATISTICS_BINNED_LIST/sp:onu-stats-id";
          }
          description
            "References PON_ONU_STATISTICS_BINNED_LIST.";
        }
        leaf me-id {
          type uint16;
          description
            "Performance management ME ID.";
        }
        leaf direction {
          type enumeration {
            enum downstream {
              description
                "Statistics entry for traffic flowing in the downstream direction.";
            }
            enum upstream {
              description
                "Statistics entry for traffic flowing in the upstream direction.";
            }
          }
          description
            "Direction of the traffic flow for this statistics entry.";
        }
        leaf broadcast-frames {
          type uint64;
          description
            "broadcast frames";
        }
        leaf crc-errored-frames {
          type uint64;
          description
            "crc errored frames";
        }
        leaf drop-events {
          type uint64;
          description
            "drop events";
        }
        leaf frames {
          type uint64;
          description
            "frames";
        }
        leaf frames-1024-to-1518-octets {
          type uint64;
          description
            "frames 1024 to 1518 octets";
        }
        leaf frames-128-to-255-octets {
          type uint64;
          description
            "frames 128 to 255 octets";
        }
        leaf frames-256-to-511-octets {
          type uint64;
          description
            "frames 256 to 511 octets";
        }
        leaf frames-512-to-1023-octets {
          type uint64;
          description
            "frames 512 to 1023 octets";
        }
        leaf frames-64-octets {
          type uint64;
          description
            "frames 64 octets";
        }
        leaf frames-65-to-127-octets {
          type uint64;
          description
            "frames 65 to 127 octets";
        }
        leaf interval-end-time {
          type uint64;
          description
            "interval end time";
        }
        leaf multicast-frames {
          type uint64;
          description
            "multicast frames";
        }
        leaf octets {
          type uint64;
          description
            "octets";
        }
        leaf oversize-frames {
          type uint64;
          description
            "oversize frames";
        }
        leaf undersize-frames {
          type uint64;
          description
            "undersize frames";
        }
      }
    }
    container PON_ONU_STATISTICS_BINNED_ONU_ETHERNET_FRAME_EXTENDED_PM_64BIT {
      description
        "PON_ONU_STATISTICS_BINNED_ONU_ETHERNET_FRAME_EXTENDED_PM_64BIT table in StateDB.";
      config false;
      list PON_ONU_STATISTICS_BINNED_ONU_ETHERNET_FRAME_EXTENDED_PM_64BIT_LIST {
        key "onu-name onu-stats-id me-id";
        description
          "GPON: MAC Bridge Port 64-bit statistics reported by ONU through OMCI.
           StateDB key: PON_ONU_STATISTICS_BINNED_ONU_ETHERNET_FRAME_EXTENDED_PM_64BIT|<onu-name>|<onu-stats-id>|<me-id>.";
        leaf onu-name {
          type leafref {
            path "/sp:sonic-pon/sp:PON_ONU_STATE/sp:PON_ONU_STATE_LIST/sp:onu-name";
          }
          description
            "References PON_ONU_STATE_LIST.";
        }
        leaf onu-stats-id {
          type leafref {
            path "/sp:sonic-pon/sp:PON_ONU_STATISTICS_BINNED/sp:PON_ONU_STATISTICS_BINNED_LIST/sp:onu-stats-id";
          }
          description
            "References PON_ONU_STATISTICS_BINNED_LIST.";
        }
        leaf me-id {
          type uint16;
          description
            "Performance management ME ID.";
        }
        leaf direction {
          type enumeration {
            enum downstream {
              description
                "Statistics entry for traffic flowing in the downstream direction.";
            }
            enum upstream {
              description
                "Statistics entry for traffic flowing in the upstream direction.";
            }
          }
          description
            "Direction of the traffic flow for this statistics entry.";
        }
        leaf broadcast-frames {
          type uint64;
          description
            "broadcast frames";
        }
        leaf crc-errored-frames {
          type uint64;
          description
            "crc errored frames";
        }
        leaf drop-events {
          type uint64;
          description
            "drop events";
        }
        leaf frames {
          type uint64;
          description
            "frames";
        }
        leaf frames-1024-to-1518-octets {
          type uint64;
          description
            "frames 1024 to 1518 octets";
        }
        leaf frames-128-to-255-octets {
          type uint64;
          description
            "frames 128 to 255 octets";
        }
        leaf frames-256-to-511-octets {
          type uint64;
          description
            "frames 256 to 511 octets";
        }
        leaf frames-512-to-1023-octets {
          type uint64;
          description
            "frames 512 to 1023 octets";
        }
        leaf frames-64-octets {
          type uint64;
          description
            "frames 64 octets";
        }
        leaf frames-65-to-127-octets {
          type uint64;
          description
            "frames 65 to 127 octets";
        }
        leaf interval-end-time {
          type uint64;
          description
            "interval end time";
        }
        leaf multicast-frames {
          type uint64;
          description
            "multicast frames";
        }
        leaf octets {
          type uint64;
          description
            "octets";
        }
        leaf oversize-frames {
          type uint64;
          description
            "oversize frames";
        }
        leaf undersize-frames {
          type uint64;
          description
            "undersize frames";
        }
      }
    }
    container PON_ONU_STATISTICS_BINNED_ONU_ETHERNET_FRAME_PM_DOWNSTREAM {
      description
        "PON_ONU_STATISTICS_BINNED_ONU_ETHERNET_FRAME_PM_DOWNSTREAM table in StateDB.";
      config false;
      list PON_ONU_STATISTICS_BINNED_ONU_ETHERNET_FRAME_PM_DOWNSTREAM_LIST {
        key "onu-name onu-stats-id me-id";
        description
          "GPON: Downstream MAC Bridge Service Profile statistics reported by ONU through OMCI.
           StateDB key: PON_ONU_STATISTICS_BINNED_ONU_ETHERNET_FRAME_PM_DOWNSTREAM|<onu-name>|<onu-stats-id>|<me-id>.";
        leaf onu-name {
          type leafref {
            path "/sp:sonic-pon/sp:PON_ONU_STATE/sp:PON_ONU_STATE_LIST/sp:onu-name";
          }
          description
            "References PON_ONU_STATE_LIST.";
        }
        leaf onu-stats-id {
          type leafref {
            path "/sp:sonic-pon/sp:PON_ONU_STATISTICS_BINNED/sp:PON_ONU_STATISTICS_BINNED_LIST/sp:onu-stats-id";
          }
          description
            "References PON_ONU_STATISTICS_BINNED_LIST.";
        }
        leaf me-id {
          type uint16;
          description
            "Performance management ME ID.";
        }
        leaf broadcast-packets {
          type uint64;
          description
            "broadcast packets";
        }
        leaf crc-errored-packets {
          type uint64;
          description
            "crc errored packets";
        }
        leaf drop-events {
          type uint64;
          description
            "drop events";
        }
        leaf interval-end-time {
          type uint64;
          description
            "interval end time";
        }
        leaf multicast-packets {
          type uint64;
          description
            "multicast packets";
        }
        leaf octets {
          type uint64;
          description
            "octets";
        }
        leaf oversize-packets {
          type uint64;
          description
            "oversize packets";
        }
        leaf packets {
          type uint64;
          description
            "packets";
        }
        leaf packets-1024-to-1518-octets {
          type uint64;
          description
            "packets 1024 to 1518 octets";
        }
        leaf packets-128-to-255-octets {
          type uint64;
          description
            "packets 128 to 255 octets";
        }
        leaf packets-256-to-511-octets {
          type uint64;
          description
            "packets 256 to 511 octets";
        }
        leaf packets-512-to-1023-octets {
          type uint64;
          description
            "packets 512 to 1023 octets";
        }
        leaf packets-64-octets {
          type uint64;
          description
            "packets 64 octets";
        }
        leaf packets-65-to-127-octets {
          type uint64;
          description
            "packets 65 to 127 octets";
        }
        leaf threshold-data-1-2-id {
          type omci-types:omci-uint16;
          description
            "threshold data 1/2 id";
        }
        leaf undersize-packets {
          type uint64;
          description
            "undersize packets";
        }
      }
    }
    container PON_ONU_STATISTICS_BINNED_ONU_ETHERNET_FRAME_PM_UPSTREAM {
      description
        "PON_ONU_STATISTICS_BINNED_ONU_ETHERNET_FRAME_PM_UPSTREAM table in StateDB.";
      config false;
      list PON_ONU_STATISTICS_BINNED_ONU_ETHERNET_FRAME_PM_UPSTREAM_LIST {
        key "onu-name onu-stats-id me-id";
        description
          "GPON: Upstream MAC Bridge Service Profile statistics reported by ONU through OMCI.
           StateDB key: PON_ONU_STATISTICS_BINNED_ONU_ETHERNET_FRAME_PM_UPSTREAM|<onu-name>|<onu-stats-id>|<me-id>.";
        leaf onu-name {
          type leafref {
            path "/sp:sonic-pon/sp:PON_ONU_STATE/sp:PON_ONU_STATE_LIST/sp:onu-name";
          }
          description
            "References PON_ONU_STATE_LIST.";
        }
        leaf onu-stats-id {
          type leafref {
            path "/sp:sonic-pon/sp:PON_ONU_STATISTICS_BINNED/sp:PON_ONU_STATISTICS_BINNED_LIST/sp:onu-stats-id";
          }
          description
            "References PON_ONU_STATISTICS_BINNED_LIST.";
        }
        leaf me-id {
          type uint16;
          description
            "Performance management ME ID.";
        }
        leaf broadcast-packets {
          type uint64;
          description
            "broadcast packets";
        }
        leaf crc-errored-packets {
          type uint64;
          description
            "crc errored packets";
        }
        leaf drop-events {
          type uint64;
          description
            "drop events";
        }
        leaf interval-end-time {
          type uint64;
          description
            "interval end time";
        }
        leaf multicast-packets {
          type uint64;
          description
            "multicast packets";
        }
        leaf octets {
          type uint64;
          description
            "octets";
        }
        leaf oversize-packets {
          type uint64;
          description
            "oversize packets";
        }
        leaf packets {
          type uint64;
          description
            "packets";
        }
        leaf packets-1024-to-1518-octets {
          type uint64;
          description
            "packets 1024 to 1518 octets";
        }
        leaf packets-128-to-255-octets {
          type uint64;
          description
            "packets 128 to 255 octets";
        }
        leaf packets-256-to-511-octets {
          type uint64;
          description
            "packets 256 to 511 octets";
        }
        leaf packets-512-to-1023-octets {
          type uint64;
          description
            "packets 512 to 1023 octets";
        }
        leaf packets-64-octets {
          type uint64;
          description
            "packets 64 octets";
        }
        leaf packets-65-to-127-octets {
          type uint64;
          description
            "packets 65 to 127 octets";
        }
        leaf threshold-data-1-2-id {
          type omci-types:omci-uint16;
          description
            "threshold data 1/2 id";
        }
        leaf undersize-packets {
          type uint64;
          description
            "undersize packets";
        }
      }
    }
    container PON_ONU_STATISTICS_BINNED_ONU_ETHERNET_PM {
      description
        "PON_ONU_STATISTICS_BINNED_ONU_ETHERNET_PM table in StateDB.";
      config false;
      list PON_ONU_STATISTICS_BINNED_ONU_ETHERNET_PM_LIST {
        key "onu-name onu-stats-id me-id";
        description
          "GPON: Ethernet UNI port statistics reported by ONU through OMCI.
           StateDB key: PON_ONU_STATISTICS_BINNED_ONU_ETHERNET_PM|<onu-name>|<onu-stats-id>|<me-id>.";
        leaf onu-name {
          type leafref {
            path "/sp:sonic-pon/sp:PON_ONU_STATE/sp:PON_ONU_STATE_LIST/sp:onu-name";
          }
          description
            "References PON_ONU_STATE_LIST.";
        }
        leaf onu-stats-id {
          type leafref {
            path "/sp:sonic-pon/sp:PON_ONU_STATISTICS_BINNED/sp:PON_ONU_STATISTICS_BINNED_LIST/sp:onu-stats-id";
          }
          description
            "References PON_ONU_STATISTICS_BINNED_LIST.";
        }
        leaf me-id {
          type uint16;
          description
            "Performance management ME ID.";
        }
        leaf alignment-error-counter {
          type uint64;
          description
            "alignment error counter";
        }
        leaf buffer-overflows-on-receive {
          type uint64;
          description
            "buffer overflows on receive";
        }
        leaf buffer-overflows-on-transmit {
          type uint64;
          description
            "buffer overflows on transmit";
        }
        leaf carrier-sense-error-counter {
          type uint64;
          description
            "carrier sense error counter";
        }
        leaf deferred-transmission-counter {
          type uint64;
          description
            "deferred transmission counter";
        }
        leaf excessive-collision-counter {
          type uint64;
          description
            "excessive collision counter";
        }
        leaf fcs-errors {
          type uint64;
          description
            "fcs errors";
        }
        leaf frames-too-long {
          type uint64;
          description
            "frames too long";
        }
        leaf internal-mac-receive-error-counter {
          type uint64;
          description
            "internal mac receive error counter";
        }
        leaf internal-mac-transmit-error-counter {
          type uint64;
          description
            "internal mac transmit error counter";
        }
        leaf interval-end-time {
          type uint64;
          description
            "interval end time";
        }
        leaf late-collision-counter {
          type uint64;
          description
            "late collision counter";
        }
        leaf multiple-collisions-frame-counter {
          type uint64;
          description
            "multiple collisions frame counter";
        }
        leaf single-collision-frame-counter {
          type uint64;
          description
            "single collision frame counter";
        }
        leaf sqe-counter {
          type uint64;
          description
            "sqe counter";
        }
        leaf threshold-data-1-2-id {
          type omci-types:omci-uint16;
          description
            "threshold data 1/2 id";
        }
      }
    }
    container PON_ONU_STATISTICS_BINNED_ONU_IP_HOST_PERF_MON_HIST_DATA {
      description
        "PON_ONU_STATISTICS_BINNED_ONU_IP_HOST_PERF_MON_HIST_DATA table in StateDB.";
      config false;
      list PON_ONU_STATISTICS_BINNED_ONU_IP_HOST_PERF_MON_HIST_DATA_LIST {
        key "onu-name onu-stats-id me-id";
        description
          "ME collects PM data related to an IP host.
           StateDB key: PON_ONU_STATISTICS_BINNED_ONU_IP_HOST_PERF_MON_HIST_DATA|<onu-name>|<onu-stats-id>|<me-id>.";
        leaf onu-name {
          type leafref {
            path "/sp:sonic-pon/sp:PON_ONU_STATE/sp:PON_ONU_STATE_LIST/sp:onu-name";
          }
          description
            "References PON_ONU_STATE_LIST.";
        }
        leaf onu-stats-id {
          type leafref {
            path "/sp:sonic-pon/sp:PON_ONU_STATISTICS_BINNED/sp:PON_ONU_STATISTICS_BINNED_LIST/sp:onu-stats-id";
          }
          description
            "References PON_ONU_STATISTICS_BINNED_LIST.";
        }
        leaf me-id {
          type uint16;
          description
            "ME Identifier for this IP host.";
        }
        leaf dns-errors {
          type uint64;
          description
            "Counts DNS errors received.";
        }
        leaf dhcp-timeouts {
          type uint64;
          description
            "Counts DHCP timeouts received.";
        }
        leaf icmp-errors {
          type uint64;
          description
            "Counts ICMP errors received.";
        }
        leaf internal-error {
          type uint64;
          description
            "Incremented whenever the ONU encounters an internal error condition such as a driver interface failure in the IP stack.";
        }
        leaf interval-end-time {
          type uint64;
          description
            "Identifies the most recently finished 15 min interval.";
        }
        leaf ip-address-conflict {
          type uint64;
          description
            "Incremented whenever the ONU detects a conflicting IP address on the network.
             A conflicting IP address is one that has the same value as the one curently assigned to the ONU.
            ";
        }
        leaf out-of-memory {
          type uint64;
          description
            "Incremented whenever the ONU encounters an out of memory condition in the IP stack.";
        }
        leaf threshold-data-1-2-id {
          type omci-types:omci-uint16;
          description
            "Points to an instance of the threshold data 1 ME that contains PM threshold values.";
        }
      }
    }
    container PON_ONU_STATISTICS_BINNED_ONU_RS232_RS485_PERF_MON_HIST_DATA {
      description
        "PON_ONU_STATISTICS_BINNED_ONU_RS232_RS485_PERF_MON_HIST_DATA table in StateDB.";
      config false;
      list PON_ONU_STATISTICS_BINNED_ONU_RS232_RS485_PERF_MON_HIST_DATA_LIST {
        key "onu-name onu-stats-id me-id";
        description
          "ME collects PM data for a RS232/RS485 interface.
           StateDB key: PON_ONU_STATISTICS_BINNED_ONU_RS232_RS485_PERF_MON_HIST_DATA|<onu-name>|<onu-stats-id>|<me-id>.";
        leaf onu-name {
          type leafref {
            path "/sp:sonic-pon/sp:PON_ONU_STATE/sp:PON_ONU_STATE_LIST/sp:onu-name";
          }
          description
            "References PON_ONU_STATE_LIST.";
        }
        leaf onu-stats-id {
          type leafref {
            path "/sp:sonic-pon/sp:PON_ONU_STATISTICS_BINNED/sp:PON_ONU_STATISTICS_BINNED_LIST/sp:onu-stats-id";
          }
          description
            "References PON_ONU_STATISTICS_BINNED_LIST.";
        }
        leaf me-id {
          type uint16;
          description
            "ME Identifier for this RS232/RS485 interface.";
        }
        leaf incoming-bytes-from-chip {
          type uint64;
          description
            "Counts the bytes received on the RS232/RS485 chipset.";
        }
        leaf incoming-bytes-from-pon {
          type uint64;
          description
            "Counts the bytes received on the PON port.";
        }
        leaf interval-end-time {
          type uint64;
          description
            "Identifies the most recently finished 15 min interval.";
        }
        leaf outgoing-bytes-from-chip {
          type uint64;
          description
            "Counts the bytes transmitted on the RS232/RS485 chipset.";
        }
        leaf outgoing-bytes-from-pon {
          type uint64;
          description
            "Counts the bytes transmitted on the PON port.";
        }
        leaf threshold-data-1-2-id {
          type omci-types:omci-uint16;
          description
            "Points to an instance of the threshold data 1 ME that contains PM threshold values.";
        }
      }
    }
    container PON_ONU_STATISTICS_BINNED_ONU_TCP_UDP_PERF_MON_HIST_DATA {
      description
        "PON_ONU_STATISTICS_BINNED_ONU_TCP_UDP_PERF_MON_HIST_DATA table in StateDB.";
      config false;
      list PON_ONU_STATISTICS_BINNED_ONU_TCP_UDP_PERF_MON_HIST_DATA_LIST {
        key "onu-name onu-stats-id me-id";
        description
          "ME collects PM data related to a TCP or UDP port.
           StateDB key: PON_ONU_STATISTICS_BINNED_ONU_TCP_UDP_PERF_MON_HIST_DATA|<onu-name>|<onu-stats-id>|<me-id>.";
        leaf onu-name {
          type leafref {
            path "/sp:sonic-pon/sp:PON_ONU_STATE/sp:PON_ONU_STATE_LIST/sp:onu-name";
          }
          description
            "References PON_ONU_STATE_LIST.";
        }
        leaf onu-stats-id {
          type leafref {
            path "/sp:sonic-pon/sp:PON_ONU_STATISTICS_BINNED/sp:PON_ONU_STATISTICS_BINNED_LIST/sp:onu-stats-id";
          }
          description
            "References PON_ONU_STATISTICS_BINNED_LIST.";
        }
        leaf me-id {
          type uint16;
          description
            "ME Identifier for this TCP or UDP port.";
        }
        leaf accept-failed {
          type uint64;
          description
            "Incremented when an attempt to accept a connection on a port fails.";
        }
        leaf bind-failed {
          type uint64;
          description
            "Incremented when an attempt by a service to bind to a port fails.";
        }
        leaf interval-end-time {
          type uint64;
          description
            "Identifies the most recently finished 15 min interval.";
        }
        leaf listen-failed {
          type uint64;
          description
            "Incremented when an attempt by a service to listen for a request on a port fails.";
        }
        leaf select-failed {
          type uint64;
          description
            "Incremented when an attempt to perform a select on a group of ports fails.";
        }
        leaf socket-failed {
          type uint64;
          description
            "Incremented when an attempt to create a socket associated with a port fails.";
        }
        leaf threshold-data-1-2-id {
          type omci-types:omci-uint16;
          description
            "Points to an instance of the threshold data 1 ME that contains PM threshold values.";
        }
      }
    }
    container PON_ONU_STATISTICS_BINNED_ONU_ENHANCED_TC_PM {
      description
        "PON_ONU_STATISTICS_BINNED_ONU_ENHANCED_TC_PM table in StateDB.";
      config false;
      list PON_ONU_STATISTICS_BINNED_ONU_ENHANCED_TC_PM_LIST {
        key "onu-name onu-stats-id me-id";
        description
          "GPON: Enhanced TC statistics reported by ONU.
           StateDB key: PON_ONU_STATISTICS_BINNED_ONU_ENHANCED_TC_PM|<onu-name>|<onu-stats-id>|<me-id>.";
        leaf onu-name {
          type leafref {
            path "/sp:sonic-pon/sp:PON_ONU_STATE/sp:PON_ONU_STATE_LIST/sp:onu-name";
          }
          description
            "References PON_ONU_STATE_LIST.";
        }
        leaf onu-stats-id {
          type leafref {
            path "/sp:sonic-pon/sp:PON_ONU_STATISTICS_BINNED/sp:PON_ONU_STATISTICS_BINNED_LIST/sp:onu-stats-id";
          }
          description
            "References PON_ONU_STATISTICS_BINNED_LIST.";
        }
        leaf me-id {
          type uint16;
          description
            "ME Identifier for this TC.";
        }
        leaf lods-event-count {
          type uint64;
          description
            "Counts the number of state transitions from O5.1 to O6";
        }
        leaf lods-event-restored-count {
          type uint64;
          description
            "Counts the number of LODS cleared events";
        }
        leaf fragment-xgem-frames {
          type uint64;
          description
            "Counts the number of XGEM frames that represent fragmented SDUs, as indicated by the LF bit = 0";
        }
        leaf interval-end-time {
          type uint64;
          description
            "Identifies the most recently finished 15 min interval";
        }
        leaf onu-reactivation-by-lods-events {
          type uint64;
          description
            "Counts the number of LODS events resulting in ONU reactivation without synchronization being reacquired";
        }
        leaf psbd-hec-error-count {
          type uint64;
          description
            "Counts HEC errors in any of the fields of the downstream physical sync block";
        }
        leaf received-bytes-in-nonidle-xgem-frames {
          type uint64;
          description
            "Counts the number of received bytes in non-idle XGEM frames";
        }
        leaf transmitted-bytes-in-nonidle-xgem-frames {
          type uint64;
          description
            "Counts the number of transmitted bytes in non-idle XGEM frames";
        }
        leaf transmitted-xgem-frames {
          type uint64;
          description
            "Counts the number of non-idle XGEM frames transmitted. If an SDU is fragmented, each fragment is an XGEM frame and is counted as such.";
        }
        leaf unknown-profile-count {
          type uint64;
          description
            "Counts the number of grants received whose specified profile was not known to the ONU";
        }
        leaf xgem-hec-lost-words-count {
          type uint64;
          description
            "Counts the number of 4 byte words lost because of an XGEM frame HEC error. In general, all XGTC
             payload following the error is lost, until the next PSBd event.
            ";
        }
        leaf xgem-key-errors {
          type uint64;
          description
            "Counts the number of downstream XGEM frames received with an invalid key specification";
        }
        leaf xgem-hec-error-count {
          type uint64;
          description
            "Counts the number of instances of an XGEM frame HEC error";
        }
        leaf xgtc-hec-error-count {
          type uint64;
          description
            "Counts HEC errors detected in the XGTC header";
        }
        leaf threshold-data-64-bit-id {
          type uint64;
          description
            "Points to an instance of the threshold data 1 ME that contains PM threshold values";
        }
      }
    }
    container PON_ONU_STATISTICS_BINNED_ONU_ETHERNET_PM3 {
      description
        "PON_ONU_STATISTICS_BINNED_ONU_ETHERNET_PM3 table in StateDB.";
      config false;
      list PON_ONU_STATISTICS_BINNED_ONU_ETHERNET_PM3_LIST {
        key "onu-name onu-stats-id me-id";
        description
          "GPON: Counters associated with ethernet messages.
           StateDB key: PON_ONU_STATISTICS_BINNED_ONU_ETHERNET_PM3|<onu-name>|<onu-stats-id>|<me-id>.";
        leaf onu-name {
          type leafref {
            path "/sp:sonic-pon/sp:PON_ONU_STATE/sp:PON_ONU_STATE_LIST/sp:onu-name";
          }
          description
            "References PON_ONU_STATE_LIST.";
        }
        leaf onu-stats-id {
          type leafref {
            path "/sp:sonic-pon/sp:PON_ONU_STATISTICS_BINNED/sp:PON_ONU_STATISTICS_BINNED_LIST/sp:onu-stats-id";
          }
          description
            "References PON_ONU_STATISTICS_BINNED_LIST.";
        }
        leaf me-id {
          type uint16;
          description
            "Performance management ME ID.";
        }
        leaf broadcast-packets {
          type uint64;
          description
            "Total number of received good packets directed to the broadcast address. This does not include multicast packets";
        }
        leaf drop-events {
          type uint64;
          description
            "Total number of events in which packets were dropped due to a lack of resources";
        }
        leaf fragments {
          type uint64;
          description
            "Total number of packets received that were less than 64 octets long";
        }
        leaf interval-end-time {
          type uint64;
          description
            "Identifies the most recently finished 15 min interval";
        }
        leaf jabbers {
          type uint64;
          description
            "Total number of packets received that were longer than 1518 octets";
        }
        leaf multicast-packets {
          type uint64;
          description
            "Total number of received good packets directed to a multicast address. This does not include broadcast packets";
        }
        leaf octets {
          type uint64;
          description
            "Total number of octets received from the CPE, including those in bad packets";
        }
        leaf packets {
          type uint64;
          description
            "Total number of packets received, including bad packets, broadcast packets and multicast packets";
        }
        leaf packets-64-octets {
          type uint64;
          description
            "Total number of received packets (including bad packets) that were 64 octets long";
        }
        leaf packets-65-to-127-octets {
          type uint64;
          description
            "Total number of received packets (including bad packets) that were 65 to 127 octets long";
        }
        leaf packets-128-to-255-octets {
          type uint64;
          description
            "Total number of received packets (including bad packets) that were 128 to 255 octets long";
        }
        leaf packets-256-to-511-octets {
          type uint64;
          description
            "Total number of received packets (including bad packets) that were 256 to 511 octets long";
        }
        leaf packets-512-to-1023-octets {
          type uint64;
          description
            "Total number of received packets (including bad packets) that were 512 to 1023 octets long";
        }
        leaf packets-1024-to-1518-octets {
          type uint64;
          description
            "Total number of received packets (including bad packets) that were 1024 to 1518 octets long";
        }
        leaf threshold-data-1-2-id {
          type omci-types:omci-uint16;
          description
            "Points to an instance of the threshold data 1 ME that contains PM threshold values";
        }
        leaf undersize-packets {
          type uint64;
          description
            "Counts the number of frames discarded due to PPPoE filtering";
        }
      }
    }
    container PON_ONU_STATISTICS_BINNED_ONU_GAL_ETHERNET_PM {
      description
        "PON_ONU_STATISTICS_BINNED_ONU_GAL_ETHERNET_PM table in StateDB.";
      config false;
      list PON_ONU_STATISTICS_BINNED_ONU_GAL_ETHERNET_PM_LIST {
        key "onu-name onu-stats-id me-id";
        description
          "GPON: Counters associated with gal ethernet messages.
           StateDB key: PON_ONU_STATISTICS_BINNED_ONU_GAL_ETHERNET_PM|<onu-name>|<onu-stats-id>|<me-id>.";
        leaf onu-name {
          type leafref {
            path "/sp:sonic-pon/sp:PON_ONU_STATE/sp:PON_ONU_STATE_LIST/sp:onu-name";
          }
          description
            "References PON_ONU_STATE_LIST.";
        }
        leaf onu-stats-id {
          type leafref {
            path "/sp:sonic-pon/sp:PON_ONU_STATISTICS_BINNED/sp:PON_ONU_STATISTICS_BINNED_LIST/sp:onu-stats-id";
          }
          description
            "References PON_ONU_STATISTICS_BINNED_LIST.";
        }
        leaf me-id {
          type uint16;
          description
            "Performance management ME ID.";
        }
        leaf discarded-downstream-frames {
          type uint64;
          description
            "Counts the number of downstream GEM frames discarded for any reason";
        }
        leaf discarded-upstream-frames {
          type uint64;
          description
            "Counts the number of upstream frames discarded prior to GEM encapsulation (due to congestion)";
        }
        leaf interval-end-time {
          type uint64;
          description
            "Identifies the most recently finished 15 min interval";
        }
        leaf threshold-data-1-2-id {
          type omci-types:omci-uint16;
          description
            "Points to an instance of the threshold data 1 ME that contains PM threshold values";
        }
      }
    }
    container PON_ONU_STATISTICS_BINNED_ONU_GEM_PORT_NETWORK_CTP_PM {
      description
        "PON_ONU_STATISTICS_BINNED_ONU_GEM_PORT_NETWORK_CTP_PM table in StateDB.";
      config false;
      list PON_ONU_STATISTICS_BINNED_ONU_GEM_PORT_NETWORK_CTP_PM_LIST {
        key "onu-name onu-stats-id me-id";
        description
          "GPON: Counters associated with gem port network ctp messages.
           StateDB key: PON_ONU_STATISTICS_BINNED_ONU_GEM_PORT_NETWORK_CTP_PM|<onu-name>|<onu-stats-id>|<me-id>.";
        leaf onu-name {
          type leafref {
            path "/sp:sonic-pon/sp:PON_ONU_STATE/sp:PON_ONU_STATE_LIST/sp:onu-name";
          }
          description
            "References PON_ONU_STATE_LIST.";
        }
        leaf onu-stats-id {
          type leafref {
            path "/sp:sonic-pon/sp:PON_ONU_STATISTICS_BINNED/sp:PON_ONU_STATISTICS_BINNED_LIST/sp:onu-stats-id";
          }
          description
            "References PON_ONU_STATISTICS_BINNED_LIST.";
        }
        leaf me-id {
          type uint16;
          description
            "Performance management ME ID.";
        }
        leaf encryption-key-errors {
          type uint64;
          description
            "Counts GEM frames with erroneous encryption key indexes. If the GEM port is not encrypted,
             this attribute counts any frame with a key index not equal to 0. If the GEM port is encrypted,
             this attribute counts any frame whose key index specifies a key that is not known to the ONU.
            ";
        }
        leaf interval-end-time {
          type uint64;
          description
            "Identifies the most recently finished 15 min interval";
        }
        leaf received-gem-frames {
          type uint64;
          description
            "Counts GEM frames received correctly on the monitored GEM port. A correctly received GEM frame
             is one that does not contain uncorrectable errors and has a valid header error check (HEC).
            ";
        }
        leaf received-payload-bytes {
          type uint64;
          description
            "Counts user payload bytes received on the monitored GEM port";
        }
        leaf threshold-data-1-2-id {
          type omci-types:omci-uint16;
          description
            "Points to an instance of the threshold data 1 ME that contains PM threshold values";
        }
        leaf transmitted-gem-frames {
          type uint64;
          description
            "Counts GEM frames transmitted on the monitored GEM port";
        }
        leaf transmitted-payload-bytes {
          type uint64;
          description
            "Counts user payload bytes transmitted on the monitored GEM port";
        }
      }
    }
    container PON_ONU_STATISTICS_BINNED_ONU_OPERATIONAL_PM {
      description
        "PON_ONU_STATISTICS_BINNED_ONU_OPERATIONAL_PM table in StateDB.";
      config false;
      list PON_ONU_STATISTICS_BINNED_ONU_OPERATIONAL_PM_LIST {
        key "onu-name onu-stats-id me-id";
        description
          "GPON: Counters associated with operational messages.
           StateDB key: PON_ONU_STATISTICS_BINNED_ONU_OPERATIONAL_PM|<onu-name>|<onu-stats-id>|<me-id>.";
        leaf onu-name {
          type leafref {
            path "/sp:sonic-pon/sp:PON_ONU_STATE/sp:PON_ONU_STATE_LIST/sp:onu-name";
          }
          description
            "References PON_ONU_STATE_LIST.";
        }
        leaf onu-stats-id {
          type leafref {
            path "/sp:sonic-pon/sp:PON_ONU_STATISTICS_BINNED/sp:PON_ONU_STATISTICS_BINNED_LIST/sp:onu-stats-id";
          }
          description
            "References PON_ONU_STATISTICS_BINNED_LIST.";
        }
        leaf me-id {
          type uint16;
          description
            "Performance management ME ID.";
        }
        leaf cpu-percent-utilization {
          type uint64;
          description
            "Maximum system CPU utilization (high water mark) during the measurement interval";
        }
        leaf errors-in-operations {
          type uint64;
          description
            "Count of the number of detected errors in operations, not due to a software error";
        }
        leaf flash-size-available {
          type uint64;
          description
            "Minimum FLASH size available during the measurement interval";
        }
        leaf flash-utilization {
          type uint64;
          description
            "Maximum FLASH size utilized during the measurement interval";
        }
        leaf interval-end-time {
          type uint64;
          description
            "Identifies the most recently finished 15 min interval.";
        }
        leaf ram-size-available {
          type uint64;
          description
            "Minimum RAM size available during the measurement interval";
        }
        leaf ram-utilization {
          type uint64;
          description
            "Maximum RAM size utilized during the measurement interval";
        }
        leaf software-errors {
          type uint64;
          description
            "Count of the number of software errors detected";
        }
        leaf threshold-data-1-2-id {
          type omci-types:omci-uint16;
          description
            "Points to an instance of the threshold data 1 ME that contains PM threshold values.";
        }
        leaf temperature-sensor-description {
          type uint64;
          description
            "A table of temperature sensor descriptions that includes the physical location on the ONU or the component being measured";
        }
        leaf temperature-sensor-value {
          type uint64;
          description
            "A table of temperature sensor values that specifies the average temperature of the ONU temperature sensor(s) during the measurement interval";
        }
      }
    }
    container PON_ONU_STATISTICS_BINNED_ONU_MAC_BRIDGE_PORT_PM {
      description
        "PON_ONU_STATISTICS_BINNED_ONU_MAC_BRIDGE_PORT_PM table in StateDB.";
      config false;
      list PON_ONU_STATISTICS_BINNED_ONU_MAC_BRIDGE_PORT_PM_LIST {
        key "onu-name onu-stats-id me-id";
        description
          "GPON: ME collects PM data related to a mac bridge port.
           StateDB key: PON_ONU_STATISTICS_BINNED_ONU_MAC_BRIDGE_PORT_PM|<onu-name>|<onu-stats-id>|<me-id>.";
        leaf onu-name {
          type leafref {
            path "/sp:sonic-pon/sp:PON_ONU_STATE/sp:PON_ONU_STATE_LIST/sp:onu-name";
          }
          description
            "References PON_ONU_STATE_LIST.";
        }
        leaf onu-stats-id {
          type leafref {
            path "/sp:sonic-pon/sp:PON_ONU_STATISTICS_BINNED/sp:PON_ONU_STATISTICS_BINNED_LIST/sp:onu-stats-id";
          }
          description
            "References PON_ONU_STATISTICS_BINNED_LIST.";
        }
        leaf me-id {
          type uint16;
          description
            "ME Identifier for this mac bridge port.";
        }
        leaf delay-exceeded-discard-counter {
          type uint64;
          description
            "Counts frames discarded on this port because transmission was delayed";
        }
        leaf forwarded-frame-counter {
          type uint64;
          description
            "Counts frames transmitted successfully on this port";
        }
        leaf interval-end-time {
          type uint64;
          description
            "Identifies the most recently finished 15 min interval";
        }
        leaf mtu-exceeded-discard-counter {
          type uint64;
          description
            "Counts frames discarded on this port because the MTU was exceeded";
        }
        leaf received-and-discarded-counter {
          type uint64;
          description
            "Counts frames received on this port that were discarded due to errors";
        }
        leaf received-frame-counter {
          type uint64;
          description
            "Counts frames received on this port";
        }
        leaf threshold-data-1-2-id {
          type omci-types:omci-uint16;
          description
            "Points to an instance of the threshold data 1 ME that contains PM threshold values";
        }
      }
    }
    container PON_ONU_STATISTICS_BINNED_ONU_XG_PON_DOWNSTREAM_MGMT_PM {
      description
        "PON_ONU_STATISTICS_BINNED_ONU_XG_PON_DOWNSTREAM_MGMT_PM table in StateDB.";
      config false;
      list PON_ONU_STATISTICS_BINNED_ONU_XG_PON_DOWNSTREAM_MGMT_PM_LIST {
        key "onu-name onu-stats-id me-id";
        description
          "GPON: Counters associated with downstream PLOAM and OMCI messages.
           StateDB key: PON_ONU_STATISTICS_BINNED_ONU_XG_PON_DOWNSTREAM_MGMT_PM|<onu-name>|<onu-stats-id>|<me-id>.";
        leaf onu-name {
          type leafref {
            path "/sp:sonic-pon/sp:PON_ONU_STATE/sp:PON_ONU_STATE_LIST/sp:onu-name";
          }
          description
            "References PON_ONU_STATE_LIST.";
        }
        leaf onu-stats-id {
          type leafref {
            path "/sp:sonic-pon/sp:PON_ONU_STATISTICS_BINNED/sp:PON_ONU_STATISTICS_BINNED_LIST/sp:onu-stats-id";
          }
          description
            "References PON_ONU_STATISTICS_BINNED_LIST.";
        }
        leaf me-id {
          type uint16;
          description
            "Performance management ME ID.";
        }
        leaf interval-end-time {
          type uint64;
          description
            "Identifies the most recently finished 15 min interval.";
        }
        leaf threshold-data-1-2-id {
          type omci-types:omci-uint16;
          description
            "Points to an instance of the threshold data 1 ME that contains PM threshold values.";
        }
        leaf ploam-mic-error-count {
          type uint64;
          description
            "Counts MIC errors detected in downstream PLOAM messages, either directed to this ONU or broadcast to all ONUs";
        }
        leaf downstream-ploam-message-count {
          type uint64;
          description
            "Counts PLOAM messages received, either directed to this ONU or broadcast to all ONUs";
        }
        leaf profile-messages-received {
          type uint64;
          description
            "Counts the number of profile messages received, either directed to this ONU or broadcast to all ONUs.";
        }
        leaf ranging-time-messages-received {
          type uint64;
          description
            "Counts the number of ranging_time messages received, either directed to this ONU or broadcast to all ONUs.";
        }
        leaf deactivate-onu-id-messages-received {
          type uint64;
          description
            "Counts the number of deactivate_ONU-ID messages received, either directed to this ONU or broadcast to all ONUs";
        }
        leaf disable-serial-number-messages-received {
          type uint64;
          description
            "Counts the number of disable_serial_number messages received, whose serial number specified this ONU";
        }
        leaf request-registration-messages-received {
          type uint64;
          description
            "Counts the number of request_registration messages received";
        }
        leaf assign-alloc-id-messages-received {
          type uint64;
          description
            "Counts the number of assign_alloc-ID messages received";
        }
        leaf key-control-messages-received {
          type uint64;
          description
            "Counts the number of key_control messages received";
        }
        leaf sleep-allow-messages-received {
          type uint64;
          description
            "Counts the number of sleep_allow messages received";
        }
        leaf baseline-omci-messages-received-count {
          type uint64;
          description
            "Counts the number of OMCI messages received in the baseline message format";
        }
        leaf extended-omci-messages-received-count {
          type uint64;
          description
            "Counts the number of OMCI messages received in the extended message format";
        }
        leaf assign-onu-id-omci-messages-received {
          type uint64;
          description
            "Counts the number of assign_ONU-ID messages received since the last reboot";
        }
        leaf omci-mic-error-count {
          type uint64;
          description
            "Counts the number of MIC errors detected in OMCI messages directed to this ONU";
        }
      }
    }
    container PON_ONU_STATISTICS_BINNED_ONU_XG_PON_UPSTREAM_MGMT_PM {
      description
        "PON_ONU_STATISTICS_BINNED_ONU_XG_PON_UPSTREAM_MGMT_PM table in StateDB.";
      config false;
      list PON_ONU_STATISTICS_BINNED_ONU_XG_PON_UPSTREAM_MGMT_PM_LIST {
        key "onu-name onu-stats-id me-id";
        description
          "GPON: Counters associated with upstream PLOAM and OMCI messages.
           StateDB key: PON_ONU_STATISTICS_BINNED_ONU_XG_PON_UPSTREAM_MGMT_PM|<onu-name>|<onu-stats-id>|<me-id>.";
        leaf onu-name {
          type leafref {
            path "/sp:sonic-pon/sp:PON_ONU_STATE/sp:PON_ONU_STATE_LIST/sp:onu-name";
          }
          description
            "References PON_ONU_STATE_LIST.";
        }
        leaf onu-stats-id {
          type leafref {
            path "/sp:sonic-pon/sp:PON_ONU_STATISTICS_BINNED/sp:PON_ONU_STATISTICS_BINNED_LIST/sp:onu-stats-id";
          }
          description
            "References PON_ONU_STATISTICS_BINNED_LIST.";
        }
        leaf me-id {
          type uint16;
          description
            "Performance management ME ID.";
        }
        leaf interval-end-time {
          type uint64;
          description
            "Identifies the most recently finished 15 min interval.";
        }
        leaf threshold-data-1-2-id {
          type omci-types:omci-uint16;
          description
            "Points to an instance of the threshold data 1 ME that contains PM threshold values.";
        }
        leaf upstream-ploam-message-count {
          type uint64;
          description
            "Counts PLOAM messages transmitted upstream, excluding acknowledge messages";
        }
        leaf serial-number-message-count {
          type uint64;
          description
            "Counts Serial_number_ONU PLOAM messages transmitted";
        }
        leaf registration-message-count {
          type uint64;
          description
            "Counts registration PLOAM messages transmitted";
        }
        leaf key-report-message-count {
          type uint64;
          description
            "Counts key_report PLOAM messages transmitted";
        }
        leaf acknowledge-message-count {
          type uint64;
          description
            "Counts acknowledge PLOAM messages transmitted. It includes all forms of acknowledgement,
             including those transmitted in response to a PLOAMu grant when the ONU has nothing to send.
            ";
        }
        leaf sleep-request-message-count {
          type uint64;
          description
            "Counts sleep_request PLOAM messages transmitted";
        }
      }
    }
    container PON_ONU_STATISTICS_ACCUMULATING_OLT_PON {
      description
        "PON_ONU_STATISTICS_ACCUMULATING_OLT_PON table in CounterDB.";
      config false;
      list PON_ONU_STATISTICS_ACCUMULATING_OLT_PON_LIST {
        key "onu-name";
        description
          "PON statistics for this ONU as represented on the OLT.
           CounterDB key: PON_ONU_STATISTICS_ACCUMULATING_OLT_PON|<onu-name>.";
        leaf onu-name {
          type leafref {
            path "/sp:sonic-pon/sp:PON_ONU_STATE/sp:PON_ONU_STATE_LIST/sp:onu-name";
          }
          description
            "References PON_ONU_STATE_LIST.";
        }
        leaf rx-optical-level {
          type decimal64 {
            fraction-digits 3;
          }
          units "dBm";
          description
            "Receive optical level.";
        }
        leaf tx-optical-level {
          type decimal64 {
            fraction-digits 3;
          }
          units "dBm";
          description
            "Transmit optical level.";
        }
        leaf rx-deregistrations {
          type uint64;
          description
            "Number of times the ONU has deregistered.";
        }
        leaf rx-registrations {
          type uint64;
          description
            "Number of times the ONU has completed registration.";
        }
        leaf fiber-distance {
          type decimal64 {
            fraction-digits 3;
          }
          units "kilometers";
          description
            "Reports the ONU fiber distance in kilometers.";
        }
        leaf equalization-delay {
          type uint64;
          units "upstream-slots(12.8ns)";
          description
            "Equalization delay assigned by the OLT to an ONU
             to ensure that the ONU's transmissions are aligned on a common
             upstream time reference.";
          reference
            "ITU-T G.9807.1 clause C.13.1";
        }
        leaf round-trip-time {
          type uint64;
          units "TQ(16ns)";
          description
            "Calculated Route Trip Time (RTT) between the OLT and ONU.";
          reference
            "IEEE 802.3av section 77.2.1.1";
        }
        leaf one-way-delay {
          type uint64;
          units "microseconds";
          description
            "One way delay reported for an ONU.";
        }
      }
    }
    container PON_ONU_STATISTICS_ACCUMULATING_OLT_PON_OMCC {
      description
        "PON_ONU_STATISTICS_ACCUMULATING_OLT_PON_OMCC table in CounterDB.";
      config false;
      list PON_ONU_STATISTICS_ACCUMULATING_OLT_PON_OMCC_LIST {
        key "onu-name";
        description
          "GPON: OMCI channel statistics for this ONU as represented on the OLT.
           CounterDB key: PON_ONU_STATISTICS_ACCUMULATING_OLT_PON_OMCC|<onu-name>.";
        leaf onu-name {
          type leafref {
            path "/sp:sonic-pon/sp:PON_ONU_STATE/sp:PON_ONU_STATE_LIST/sp:onu-name";
          }
          description
            "References PON_ONU_STATE_LIST.";
        }
        leaf bad-key-exchanges {
          type uint64;
          description
            "Bad Key Exchanges";
        }
        leaf enable-count {
          type uint64;
          description
            "Number of times the OLT-Service was activated.";
        }
        leaf good-key-exchanges {
          type uint64;
          description
            "Good Key Exchanges";
        }
        leaf omci-oam-requests {
          type uint64;
          description
            "OMCI/OAM Requests";
        }
        leaf omci-oam-resp-time-avg {
          type uint64;
          units "microseconds";
          description
            "OMCI/OAM Resp Time Avg";
        }
        leaf omci-oam-resp-time-max {
          type uint64;
          units "microseconds";
          description
            "OMCI/OAM Resp Time Max";
        }
        leaf omci-oam-resp-time-min {
          type uint64;
          units "microseconds";
          description
            "OMCI/OAM Resp Time Min";
        }
        leaf omci-oam-responses {
          type uint64;
          description
            "OMCI/OAM Responses";
        }
        leaf omci-oam-time-to-send-avg {
          type uint64;
          units "microseconds";
          description
            "OMCI/OAM Time to Send Avg";
        }
        leaf omci-oam-time-to-send-max {
          type uint64;
          units "microseconds";
          description
            "OMCI/OAM Time to Send Max";
        }
        leaf omci-oam-time-to-send-min {
          type uint64;
          units "microseconds";
          description
            "OMCI/OAM Time to Send Min";
        }
        leaf omci-oam-timeouts {
          type uint64;
          description
            "OMCI/OAM Timeouts";
        }
        leaf ploam-timeouts {
          type uint64;
          description
            "PLOAM Timeouts";
        }
        leaf rx-all-bandwidth-reqs {
          type uint64;
          description
            "Receive All Bandwidth Reqs";
        }
        leaf rx-bw-best-effort-sla-util {
          type uint64;
          description
            "Receive BW Best Effort SLA Util";
        }
        leaf rx-bw-best-effort-sla-bps {
          type uint64;
          description
            "Receive BW Best Effort SLA bps";
        }
        leaf rx-bw-fixed-sla-util {
          type uint64;
          description
            "Receive BW Fixed SLA Util";
        }
        leaf rx-bw-fixed-sla-bps {
          type uint64;
          description
            "Receive BW Fixed SLA bps";
        }
        leaf rx-bw-guaranteed-sla-util {
          type uint64;
          description
            "Receive BW Guaranteed SLA Util";
        }
        leaf rx-bw-guaranteed-sla-bps {
          type uint64;
          description
            "Receive BW Guaranteed SLA bps";
        }
        leaf rx-bw-total-sla-util {
          type uint64;
          description
            "Receive BW Total SLA Util";
        }
        leaf rx-bw-total-sla-bps {
          type uint64;
          description
            "Receive BW Total SLA bps";
        }
        leaf rx-bad-icv-drops {
          type uint64;
          description
            "Receive Bad ICV Drops";
        }
        leaf rx-bandwidth-reqs {
          type uint64;
          description
            "Receive Bandwidth Reqs";
        }
        leaf rx-crc32-drops {
          type uint64;
          description
            "Receive CRC32 Drops";
        }
        leaf rx-crc8-errors {
          type uint64;
          description
            "Receive CRC8 Errors";
        }
        leaf rx-control-octets {
          type uint64;
          description
            "Receive Control Octets";
        }
        leaf rx-empty-slots {
          type uint64;
          description
            "Receive Empty Slots";
        }
        leaf rx-encrypted-frames {
          type uint64;
          description
            "Receive Encrypted Frames";
        }
        leaf rx-encrypted-octets {
          type uint64;
          description
            "Receive Encrypted Octets";
        }
        leaf rx-encrypted-segments {
          type uint64;
          description
            "Receive Encrypted Segments";
        }
        leaf rx-errored-bip-bits {
          type uint64;
          description
            "Receive Errored BIP Bits";
        }
        leaf rx-errored-bip-blocks {
          type uint64;
          description
            "Receive Errored BIP Blocks";
        }
        leaf rx-fec-corrected-blocks {
          type uint64;
          description
            "Receive FEC Corrected Blocks";
        }
        leaf rx-fec-corrections {
          type uint64;
          description
            "Receive FEC Corrections";
        }
        leaf rx-fec-good-blocks {
          type uint64;
          description
            "Receive FEC Good Blocks";
        }
        leaf rx-fec-uncorrectable-blocks {
          type uint64;
          description
            "Receive FEC Uncorrectable Blocks";
        }
        leaf rx-filtered-frames {
          type uint64;
          description
            "Receive Filtered Frames";
        }
        leaf rx-frames-1024_1518 {
          type uint64;
          description
            "Receive Frames 1024-1518";
        }
        leaf rx-frames-128_255 {
          type uint64;
          description
            "Receive Frames 128-255";
        }
        leaf rx-frames-1519_plus {
          type uint64;
          description
            "Receive Frames 1519-Plus";
        }
        leaf rx-frames-256_511 {
          type uint64;
          description
            "Receive Frames 256-511";
        }
        leaf rx-frames-512_1023 {
          type uint64;
          description
            "Receive Frames 512-1023";
        }
        leaf rx-frames-64 {
          type uint64;
          description
            "Receive Frames 64";
        }
        leaf rx-frames-65_127 {
          type uint64;
          description
            "Receive Frames 65-127";
        }
        leaf rx-frames-green {
          type uint64;
          description
            "Receive Frames Green";
        }
        leaf rx-good-bip-blocks {
          type uint64;
          description
            "Receive Good BIP Blocks";
        }
        leaf rx-hec-errors {
          type uint64;
          description
            "Receive HEC Errors";
        }
        leaf rx-idle-octets {
          type uint64;
          description
            "Receive Idle Octets";
        }
        leaf rx-key-mismatch-octets {
          type uint64;
          description
            "Receive Key Mismatch Octets";
        }
        leaf rx-mpcp-ploam {
          type uint64;
          description
            "Receive MPCP/PLOAM";
        }
        leaf rx-multi-broadcast-octets {
          type uint64;
          description
            "Receive Multi/Broadcast Octets";
        }
        leaf rx-oam {
          type uint64;
          description
            "Receive OAM";
        }
        leaf rx-overflow-drops {
          type uint64;
          description
            "Receive Overflow Drops";
        }
        leaf rx-overflow-octets {
          type uint64;
          description
            "Receive Overflow Octets";
        }
        leaf rx-plain-frames {
          type uint64;
          description
            "Receive Plain Frames";
        }
        leaf rx-plain-octets {
          type uint64;
          description
            "Receive Plain Octets";
        }
        leaf rx-plain-segments {
          type uint64;
          description
            "Receive Plain Segments";
        }
        leaf rx-ploam-mic-errors {
          type uint64;
          description
            "Receive PLOAM MIC Errors";
        }
        leaf rx-reports {
          type uint64;
          description
            "Receive REPORTs";
        }
        leaf rx-rate-bps {
          type uint64;
          description
            "Receive Rate bps";
        }
        leaf rx-security-drop-octets {
          type uint64;
          description
            "Receive Security Drop Octets";
        }
        leaf rx-too-long-drops {
          type uint64;
          description
            "Receive Too Long Drops";
        }
        leaf rx-too-short-drops {
          type uint64;
          description
            "Receive Too Short Drops";
        }
        leaf rx-total-octets {
          type uint64;
          description
            "Receive Total Octets";
        }
        leaf rx-unicast-octets {
          type uint64;
          description
            "Receive Unicast Octets";
        }
        leaf tx-bw-best-effort-sla-util {
          type uint64;
          description
            "Transmit BW Best Effort SLA Util";
        }
        leaf tx-bw-best-effort-sla-bps {
          type uint64;
          description
            "Transmit BW Best Effort SLA bps";
        }
        leaf tx-bw-guaranteed-sla-util {
          type uint64;
          description
            "Transmit BW Guaranteed SLA Util";
        }
        leaf tx-bw-guaranteed-sla-bps {
          type uint64;
          description
            "Transmit BW Guaranteed SLA bps";
        }
        leaf tx-bw-total-sla-util {
          type uint64;
          description
            "Transmit BW Total SLA Util";
        }
        leaf tx-bw-total-sla-bps {
          type uint64;
          description
            "Transmit BW Total SLA bps";
        }
        leaf tx-bandwidth-reqs {
          type uint64;
          description
            "Transmit Bandwidth Reqs";
        }
        leaf tx-control-octets {
          type uint64;
          description
            "Transmit Control Octets";
        }
        leaf tx-encrypted-frames {
          type uint64;
          description
            "Transmit Encrypted Frames";
        }
        leaf tx-encrypted-octets {
          type uint64;
          description
            "Transmit Encrypted Octets";
        }
        leaf tx-encrypted-segments {
          type uint64;
          description
            "Transmit Encrypted Segments";
        }
        leaf tx-frames-1024_1518 {
          type uint64;
          description
            "Transmit Frames 1024-1518";
        }
        leaf tx-frames-128_255 {
          type uint64;
          description
            "Transmit Frames 128-255";
        }
        leaf tx-frames-1519_plus {
          type uint64;
          description
            "Transmit Frames 1519-Plus";
        }
        leaf tx-frames-256_511 {
          type uint64;
          description
            "Transmit Frames 256-511";
        }
        leaf tx-frames-512_1023 {
          type uint64;
          description
            "Transmit Frames 512-1023";
        }
        leaf tx-frames-64 {
          type uint64;
          description
            "Transmit Frames 64";
        }
        leaf tx-frames-65_127 {
          type uint64;
          description
            "Transmit Frames 65-127";
        }
        leaf tx-frames-broadcast {
          type uint64;
          description
            "Transmit Frames Broadcast";
        }
        leaf tx-frames-green {
          type uint64;
          description
            "Transmit Frames Green";
        }
        leaf tx-frames-multicast {
          type uint64;
          description
            "Transmit Frames Multicast";
        }
        leaf tx-frames-unicast {
          type uint64;
          description
            "Transmit Frames Unicast";
        }
        leaf tx-gates {
          type uint64;
          description
            "Transmit GATEs";
        }
        leaf tx-grant-ups-tq {
          type uint64;
          description
            "Transmit Grant UPS Tq";
        }
        leaf tx-mpcp-ploam {
          type uint64;
          description
            "Transmit MPCP/PLOAM";
        }
        leaf tx-multi-broadcast-octets {
          type uint64;
          description
            "Transmit Multi/Broadcast Octets";
        }
        leaf tx-oam {
          type uint64;
          description
            "Transmit OAM";
        }
        leaf tx-plain-frames {
          type uint64;
          description
            "Transmit Plain Frames";
        }
        leaf tx-plain-octets {
          type uint64;
          description
            "Transmit Plain Octets";
        }
        leaf tx-plain-segments {
          type uint64;
          description
            "Transmit Plain Segments";
        }
        leaf tx-ploam-ds-ranging-time {
          type uint64;
          description
            "Transmit PLOAM DS Ranging Time";
        }
        leaf tx-rate-bps {
          type uint64;
          description
            "Transmit Rate bps";
        }
        leaf tx-total-octets {
          type uint64;
          description
            "Transmit Total Octets";
        }
        leaf tx-unicast-octets {
          type uint64;
          description
            "Transmit Unicast Octets";
        }
        leaf tx-upstream-slots {
          type uint64;
          description
            "Transmit Upstream Slots";
        }
      }
    }
    container PON_ONU_STATISTICS_ACCUMULATING_ONU_PON {
      description
        "PON_ONU_STATISTICS_ACCUMULATING_ONU_PON table in CounterDB.";
      config false;
      list PON_ONU_STATISTICS_ACCUMULATING_ONU_PON_LIST {
        key "onu-name";
        description
          "PON statistics reported by ONU.
           CounterDB key: PON_ONU_STATISTICS_ACCUMULATING_ONU_PON|<onu-name>.";
        leaf onu-name {
          type leafref {
            path "/sp:sonic-pon/sp:PON_ONU_STATE/sp:PON_ONU_STATE_LIST/sp:onu-name";
          }
          description
            "References PON_ONU_STATE_LIST.";
        }
        leaf rx-optical-level {
          type decimal64 {
            fraction-digits 3;
          }
          units "dBm";
          description
            "Receive Optical Level";
        }
        leaf tx-optical-level {
          type decimal64 {
            fraction-digits 3;
          }
          units "dBm";
          description
            "Transmit Optical Level";
        }
      }
    }
    container PON_ONU_STATISTICS_ACCUMULATING_OLT_PON_SERVICE {
      description
        "PON_ONU_STATISTICS_ACCUMULATING_OLT_PON_SERVICE table in CounterDB.";
      config false;
      list PON_ONU_STATISTICS_ACCUMULATING_OLT_PON_SERVICE_LIST {
        key "onu-name onu-id";
        description
          "OLT-Service Port statistics for this ONU as represented on the OLT.
           CounterDB key: PON_ONU_STATISTICS_ACCUMULATING_OLT_PON_SERVICE|<onu-name>|<onu-id>.";
        leaf onu-name {
          type leafref {
            path "/sp:sonic-pon/sp:PON_ONU_STATE/sp:PON_ONU_STATE_LIST/sp:onu-name";
          }
          description
            "References PON_ONU_STATE_LIST.";
        }
        leaf onu-id {
          type uint8;
          description
            "OLT-Service Port number.";
        }
        leaf bad-key-exchanges {
          type uint64;
          description
            "Bad Key Exchanges";
        }
        leaf enable-count {
          type uint64;
          description
            "Number of times the OLT-Service was activated.";
        }
        leaf good-key-exchanges {
          type uint64;
          description
            "Good Key Exchanges";
        }
        leaf omci-oam-requests {
          type uint64;
          description
            "OMCI/OAM Requests";
        }
        leaf omci-oam-resp-time-avg {
          type uint64;
          units "microseconds";
          description
            "OMCI/OAM Resp Time Avg";
        }
        leaf omci-oam-resp-time-max {
          type uint64;
          units "microseconds";
          description
            "OMCI/OAM Resp Time Max";
        }
        leaf omci-oam-resp-time-min {
          type uint64;
          units "microseconds";
          description
            "OMCI/OAM Resp Time Min";
        }
        leaf omci-oam-responses {
          type uint64;
          description
            "OMCI/OAM Responses";
        }
        leaf omci-oam-time-to-send-avg {
          type uint64;
          units "microseconds";
          description
            "OMCI/OAM Time to Send Avg";
        }
        leaf omci-oam-time-to-send-max {
          type uint64;
          units "microseconds";
          description
            "OMCI/OAM Time to Send Max";
        }
        leaf omci-oam-time-to-send-min {
          type uint64;
          units "microseconds";
          description
            "OMCI/OAM Time to Send Min";
        }
        leaf omci-oam-timeouts {
          type uint64;
          description
            "OMCI/OAM Timeouts";
        }
        leaf ploam-timeouts {
          type uint64;
          description
            "PLOAM Timeouts";
        }
        leaf rx-all-bandwidth-reqs {
          type uint64;
          description
            "Receive All Bandwidth Reqs";
        }
        leaf rx-bw-best-effort-sla-util {
          type uint64;
          description
            "Receive BW Best Effort SLA Util";
        }
        leaf rx-bw-best-effort-sla-bps {
          type uint64;
          description
            "Receive BW Best Effort SLA bps";
        }
        leaf rx-bw-fixed-sla-util {
          type uint64;
          description
            "Receive BW Fixed SLA Util";
        }
        leaf rx-bw-fixed-sla-bps {
          type uint64;
          description
            "Receive BW Fixed SLA bps";
        }
        leaf rx-bw-guaranteed-sla-util {
          type uint64;
          description
            "Receive BW Guaranteed SLA Util";
        }
        leaf rx-bw-guaranteed-sla-bps {
          type uint64;
          description
            "Receive BW Guaranteed SLA bps";
        }
        leaf rx-bw-total-sla-util {
          type uint64;
          description
            "Receive BW Total SLA Util";
        }
        leaf rx-bw-total-sla-bps {
          type uint64;
          description
            "Receive BW Total SLA bps";
        }
        leaf rx-bad-icv-drops {
          type uint64;
          description
            "Receive Bad ICV Drops";
        }
        leaf rx-bandwidth-reqs {
          type uint64;
          description
            "Receive Bandwidth Reqs";
        }
        leaf rx-crc32-drops {
          type uint64;
          description
            "Receive CRC32 Drops";
        }
        leaf rx-crc8-errors {
          type uint64;
          description
            "Receive CRC8 Errors";
        }
        leaf rx-control-octets {
          type uint64;
          description
            "Receive Control Octets";
        }
        leaf rx-empty-slots {
          type uint64;
          description
            "Receive Empty Slots";
        }
        leaf rx-encrypted-frames {
          type uint64;
          description
            "Receive Encrypted Frames";
        }
        leaf rx-encrypted-octets {
          type uint64;
          description
            "Receive Encrypted Octets";
        }
        leaf rx-encrypted-segments {
          type uint64;
          description
            "Receive Encrypted Segments";
        }
        leaf rx-errored-bip-bits {
          type uint64;
          description
            "Receive Errored BIP Bits";
        }
        leaf rx-errored-bip-blocks {
          type uint64;
          description
            "Receive Errored BIP Blocks";
        }
        leaf rx-fec-corrected-blocks {
          type uint64;
          description
            "Receive FEC Corrected Blocks";
        }
        leaf rx-fec-corrections {
          type uint64;
          description
            "Receive FEC Corrections";
        }
        leaf rx-fec-good-blocks {
          type uint64;
          description
            "Receive FEC Good Blocks";
        }
        leaf rx-fec-uncorrectable-blocks {
          type uint64;
          description
            "Receive FEC Uncorrectable Blocks";
        }
        leaf rx-filtered-frames {
          type uint64;
          description
            "Receive Filtered Frames";
        }
        leaf rx-frames-1024_1518 {
          type uint64;
          description
            "Receive Frames 1024-1518";
        }
        leaf rx-frames-128_255 {
          type uint64;
          description
            "Receive Frames 128-255";
        }
        leaf rx-frames-1519_plus {
          type uint64;
          description
            "Receive Frames 1519-Plus";
        }
        leaf rx-frames-256_511 {
          type uint64;
          description
            "Receive Frames 256-511";
        }
        leaf rx-frames-512_1023 {
          type uint64;
          description
            "Receive Frames 512-1023";
        }
        leaf rx-frames-64 {
          type uint64;
          description
            "Receive Frames 64";
        }
        leaf rx-frames-65_127 {
          type uint64;
          description
            "Receive Frames 65-127";
        }
        leaf rx-frames-green {
          type uint64;
          description
            "Receive Frames Green";
        }
        leaf rx-good-bip-blocks {
          type uint64;
          description
            "Receive Good BIP Blocks";
        }
        leaf rx-hec-errors {
          type uint64;
          description
            "Receive HEC Errors";
        }
        leaf rx-idle-octets {
          type uint64;
          description
            "Receive Idle Octets";
        }
        leaf rx-key-mismatch-octets {
          type uint64;
          description
            "Receive Key Mismatch Octets";
        }
        leaf rx-mpcp-ploam {
          type uint64;
          description
            "Receive MPCP/PLOAM";
        }
        leaf rx-multi-broadcast-octets {
          type uint64;
          description
            "Receive Multi/Broadcast Octets";
        }
        leaf rx-overflow-drops {
          type uint64;
          description
            "Receive Overflow Drops";
        }
        leaf rx-overflow-octets {
          type uint64;
          description
            "Receive Overflow Octets";
        }
        leaf rx-plain-frames {
          type uint64;
          description
            "Receive Plain Frames";
        }
        leaf rx-plain-octets {
          type uint64;
          description
            "Receive Plain Octets";
        }
        leaf rx-plain-segments {
          type uint64;
          description
            "Receive Plain Segments";
        }
        leaf rx-ploam-mic-errors {
          type uint64;
          description
            "Receive PLOAM MIC Errors";
        }
        leaf rx-rate-bps {
          type uint64;
          description
            "Receive Rate bps";
        }
        leaf rx-security-drop-octets {
          type uint64;
          description
            "Receive Security Drop Octets";
        }
        leaf rx-too-long-drops {
          type uint64;
          description
            "Receive Too Long Drops";
        }
        leaf rx-too-short-drops {
          type uint64;
          description
            "Receive Too Short Drops";
        }
        leaf rx-total-octets {
          type uint64;
          description
            "Receive Total Octets";
        }
        leaf rx-unicast-octets {
          type uint64;
          description
            "Receive Unicast Octets";
        }
        leaf tx-bw-best-effort-sla-util {
          type uint64;
          description
            "Transmit BW Best Effort SLA Util";
        }
        leaf tx-bw-best-effort-sla-bps {
          type uint64;
          description
            "Transmit BW Best Effort SLA bps";
        }
        leaf tx-bw-guaranteed-sla-util {
          type uint64;
          description
            "Transmit BW Guaranteed SLA Util";
        }
        leaf tx-bw-guaranteed-sla-bps {
          type uint64;
          description
            "Transmit BW Guaranteed SLA bps";
        }
        leaf tx-bw-total-sla-util {
          type uint64;
          description
            "Transmit BW Total SLA Util";
        }
        leaf tx-bw-total-sla-bps {
          type uint64;
          description
            "Transmit BW Total SLA bps";
        }
        leaf tx-bandwidth-reqs {
          type uint64;
          description
            "Transmit Bandwidth Reqs";
        }
        leaf tx-control-octets {
          type uint64;
          description
            "Transmit Control Octets";
        }
        leaf tx-encrypted-frames {
          type uint64;
          description
            "Transmit Encrypted Frames";
        }
        leaf tx-encrypted-octets {
          type uint64;
          description
            "Transmit Encrypted Octets";
        }
        leaf tx-encrypted-segments {
          type uint64;
          description
            "Transmit Encrypted Segments";
        }
        leaf tx-frames-1024_1518 {
          type uint64;
          description
            "Transmit Frames 1024-1518";
        }
        leaf tx-frames-128_255 {
          type uint64;
          description
            "Transmit Frames 128-255";
        }
        leaf tx-frames-1519_plus {
          type uint64;
          description
            "Transmit Frames 1519-Plus";
        }
        leaf tx-frames-256_511 {
          type uint64;
          description
            "Transmit Frames 256-511";
        }
        leaf tx-frames-512_1023 {
          type uint64;
          description
            "Transmit Frames 512-1023";
        }
        leaf tx-frames-64 {
          type uint64;
          description
            "Transmit Frames 64";
        }
        leaf tx-frames-65_127 {
          type uint64;
          description
            "Transmit Frames 65-127";
        }
        leaf tx-frames-broadcast {
          type uint64;
          description
            "Transmit Frames Broadcast";
        }
        leaf tx-frames-green {
          type uint64;
          description
            "Transmit Frames Green";
        }
        leaf tx-frames-multicast {
          type uint64;
          description
            "Transmit Frames Multicast";
        }
        leaf tx-frames-unicast {
          type uint64;
          description
            "Transmit Frames Unicast";
        }
        leaf tx-mpcp-ploam {
          type uint64;
          description
            "Transmit MPCP/PLOAM";
        }
        leaf tx-multi-broadcast-octets {
          type uint64;
          description
            "Transmit Multi/Broadcast Octets";
        }
        leaf tx-plain-frames {
          type uint64;
          description
            "Transmit Plain Frames";
        }
        leaf tx-plain-octets {
          type uint64;
          description
            "Transmit Plain Octets";
        }
        leaf tx-plain-segments {
          type uint64;
          description
            "Transmit Plain Segments";
        }
        leaf tx-ploam-ds-ranging-time {
          type uint64;
          description
            "Transmit PLOAM DS Ranging Time";
        }
        leaf tx-rate-bps {
          type uint64;
          description
            "Transmit Rate bps";
        }
        leaf tx-total-octets {
          type uint64;
          description
            "Transmit Total Octets";
        }
        leaf tx-unicast-octets {
          type uint64;
          description
            "Transmit Unicast Octets";
        }
        leaf tx-upstream-slots {
          type uint64;
          description
            "Transmit Upstream Slots";
        }
      }
    }
    container PON_ONU_STATISTICS_ACCUMULATING_ONU_FEC_PM {
      description
        "PON_ONU_STATISTICS_ACCUMULATING_ONU_FEC_PM table in CounterDB.";
      config false;
      list PON_ONU_STATISTICS_ACCUMULATING_ONU_FEC_PM_LIST {
        key "onu-name onu-id";
        description
          "GPON: FEC statistics reported by ONU through OMCI.
           CounterDB key: PON_ONU_STATISTICS_ACCUMULATING_ONU_FEC_PM|<onu-name>|<onu-id>.";
        leaf onu-name {
          type leafref {
            path "/sp:sonic-pon/sp:PON_ONU_STATE/sp:PON_ONU_STATE_LIST/sp:onu-name";
          }
          description
            "References PON_ONU_STATE_LIST.";
        }
        leaf onu-id {
          type uint16;
          description
            "Performance management ME ID.";
        }
        leaf corrected-bytes {
          type uint64;
          description
            "corrected bytes";
        }
        leaf corrected-code-words {
          type uint64;
          description
            "corrected code words";
        }
        leaf fec-seconds {
          type uint64;
          description
            "fec seconds";
        }
        leaf interval-end-time {
          type uint64;
          description
            "interval end time";
        }
        leaf threshold-data-1-2-id {
          type omci-types:omci-uint16;
          description
            "threshold data 1/2 id";
        }
        leaf total-code-words {
          type uint64;
          description
            "total code words";
        }
        leaf uncorrectable-code-words {
          type uint64;
          description
            "uncorrectable code words";
        }
      }
    }
    container PON_ONU_STATISTICS_ACCUMULATING_ONU_ENHANCED_TC_PM {
      description
        "PON_ONU_STATISTICS_ACCUMULATING_ONU_ENHANCED_TC_PM table in CounterDB.";
      config false;
      list PON_ONU_STATISTICS_ACCUMULATING_ONU_ENHANCED_TC_PM_LIST {
        key "onu-name onu-id";
        description
          "GPON: Enhanced TC statistics reported by ONU.
           CounterDB key: PON_ONU_STATISTICS_ACCUMULATING_ONU_ENHANCED_TC_PM|<onu-name>|<onu-id>.";
        leaf onu-name {
          type leafref {
            path "/sp:sonic-pon/sp:PON_ONU_STATE/sp:PON_ONU_STATE_LIST/sp:onu-name";
          }
          description
            "References PON_ONU_STATE_LIST.";
        }
        leaf onu-id {
          type uint16;
          description
            "ME Identifier for this TC.";
        }
        leaf lods-event-count {
          type uint64;
          description
            "Counts the number of state transitions from O5.1 to O6";
        }
        leaf lods-event-restored-count {
          type uint64;
          description
            "Counts the number of LODS cleared events";
        }
        leaf fragment-xgem-frames {
          type uint64;
          description
            "Counts the number of XGEM frames that represent fragmented SDUs, as indicated by the LF bit = 0";
        }
        leaf interval-end-time {
          type uint64;
          description
            "Identifies the most recently finished 15 min interval";
        }
        leaf onu-reactivation-by-lods-events {
          type uint64;
          description
            "Counts the number of LODS events resulting in ONU reactivation without synchronization being reacquired";
        }
        leaf psbd-hec-error-count {
          type uint64;
          description
            "Counts HEC errors in any of the fields of the downstream physical sync block";
        }
        leaf received-bytes-in-nonidle-xgem-frames {
          type uint64;
          description
            "Counts the number of received bytes in non-idle XGEM frames";
        }
        leaf transmitted-bytes-in-nonidle-xgem-frames {
          type uint64;
          description
            "Counts the number of transmitted bytes in non-idle XGEM frames";
        }
        leaf transmitted-xgem-frames {
          type uint64;
          description
            "Counts the number of non-idle XGEM frames transmitted. If an SDU is fragmented, each fragment is an XGEM frame and is counted as such.";
        }
        leaf unknown-profile-count {
          type uint64;
          description
            "Counts the number of grants received whose specified profile was not known to the ONU";
        }
        leaf xgem-hec-lost-words-count {
          type uint64;
          description
            "Counts the number of 4 byte words lost because of an XGEM frame HEC error. In general, all XGTC
             payload following the error is lost, until the next PSBd event.
            ";
        }
        leaf xgem-key-errors {
          type uint64;
          description
            "Counts the number of downstream XGEM frames received with an invalid key specification";
        }
        leaf xgem-hec-error-count {
          type uint64;
          description
            "Counts the number of instances of an XGEM frame HEC error";
        }
        leaf xgtc-hec-error-count {
          type uint64;
          description
            "Counts HEC errors detected in the XGTC header";
        }
        leaf threshold-data-64-bit-id {
          type uint64;
          description
            "Points to an instance of the threshold data 1 ME that contains PM threshold values";
        }
      }
    }
    container PON_ONU_STATISTICS_ACCUMULATING_ONU_ETHERNET_FRAME_EXTENDED_PM {
      description
        "PON_ONU_STATISTICS_ACCUMULATING_ONU_ETHERNET_FRAME_EXTENDED_PM table in CounterDB.";
      config false;
      list PON_ONU_STATISTICS_ACCUMULATING_ONU_ETHERNET_FRAME_EXTENDED_PM_LIST {
        key "onu-name onu-id";
        description
          "GPON: MAC Bridge Port statistics reported by ONU through OMCI.
           CounterDB key: PON_ONU_STATISTICS_ACCUMULATING_ONU_ETHERNET_FRAME_EXTENDED_PM|<onu-name>|<onu-id>.";
        leaf onu-name {
          type leafref {
            path "/sp:sonic-pon/sp:PON_ONU_STATE/sp:PON_ONU_STATE_LIST/sp:onu-name";
          }
          description
            "References PON_ONU_STATE_LIST.";
        }
        leaf onu-id {
          type uint16;
          description
            "Performance management ME ID.";
        }
        leaf direction {
          type enumeration {
            enum downstream {
              description
                "Statistics entry for traffic flowing in the downstream direction.";
            }
            enum upstream {
              description
                "Statistics entry for traffic flowing in the upstream direction.";
            }
          }
          description
            "Direction of the traffic flow for this statistics entry.";
        }
        leaf broadcast-frames {
          type uint64;
          description
            "broadcast frames";
        }
        leaf crc-errored-frames {
          type uint64;
          description
            "crc errored frames";
        }
        leaf drop-events {
          type uint64;
          description
            "drop events";
        }
        leaf frames {
          type uint64;
          description
            "frames";
        }
        leaf frames-1024-to-1518-octets {
          type uint64;
          description
            "frames 1024 to 1518 octets";
        }
        leaf frames-128-to-255-octets {
          type uint64;
          description
            "frames 128 to 255 octets";
        }
        leaf frames-256-to-511-octets {
          type uint64;
          description
            "frames 256 to 511 octets";
        }
        leaf frames-512-to-1023-octets {
          type uint64;
          description
            "frames 512 to 1023 octets";
        }
        leaf frames-64-octets {
          type uint64;
          description
            "frames 64 octets";
        }
        leaf frames-65-to-127-octets {
          type uint64;
          description
            "frames 65 to 127 octets";
        }
        leaf interval-end-time {
          type uint64;
          description
            "interval end time";
        }
        leaf multicast-frames {
          type uint64;
          description
            "multicast frames";
        }
        leaf octets {
          type uint64;
          description
            "octets";
        }
        leaf oversize-frames {
          type uint64;
          description
            "oversize frames";
        }
        leaf undersize-frames {
          type uint64;
          description
            "undersize frames";
        }
      }
    }
    container PON_ONU_STATISTICS_ACCUMULATING_ONU_ETHERNET_FRAME_EXTENDED_PM_64BIT {
      description
        "PON_ONU_STATISTICS_ACCUMULATING_ONU_ETHERNET_FRAME_EXTENDED_PM_64BIT table in CounterDB.";
      config false;
      list PON_ONU_STATISTICS_ACCUMULATING_ONU_ETHERNET_FRAME_EXTENDED_PM_64BIT_LIST {
        key "onu-name onu-id";
        description
          "GPON: MAC Bridge Port 64-bit statistics reported by ONU through OMCI.
           CounterDB key: PON_ONU_STATISTICS_ACCUMULATING_ONU_ETHERNET_FRAME_EXTENDED_PM_64BIT|<onu-name>|<onu-id>.";
        leaf onu-name {
          type leafref {
            path "/sp:sonic-pon/sp:PON_ONU_STATE/sp:PON_ONU_STATE_LIST/sp:onu-name";
          }
          description
            "References PON_ONU_STATE_LIST.";
        }
        leaf onu-id {
          type uint16;
          description
            "Performance management ME ID.";
        }
        leaf direction {
          type enumeration {
            enum downstream {
              description
                "Statistics entry for traffic flowing in the downstream direction.";
            }
            enum upstream {
              description
                "Statistics entry for traffic flowing in the upstream direction.";
            }
          }
          description
            "Direction of the traffic flow for this statistics entry.";
        }
        leaf broadcast-frames {
          type uint64;
          description
            "broadcast frames";
        }
        leaf crc-errored-frames {
          type uint64;
          description
            "crc errored frames";
        }
        leaf drop-events {
          type uint64;
          description
            "drop events";
        }
        leaf frames {
          type uint64;
          description
            "frames";
        }
        leaf frames-1024-to-1518-octets {
          type uint64;
          description
            "frames 1024 to 1518 octets";
        }
        leaf frames-128-to-255-octets {
          type uint64;
          description
            "frames 128 to 255 octets";
        }
        leaf frames-256-to-511-octets {
          type uint64;
          description
            "frames 256 to 511 octets";
        }
        leaf frames-512-to-1023-octets {
          type uint64;
          description
            "frames 512 to 1023 octets";
        }
        leaf frames-64-octets {
          type uint64;
          description
            "frames 64 octets";
        }
        leaf frames-65-to-127-octets {
          type uint64;
          description
            "frames 65 to 127 octets";
        }
        leaf interval-end-time {
          type uint64;
          description
            "interval end time";
        }
        leaf multicast-frames {
          type uint64;
          description
            "multicast frames";
        }
        leaf octets {
          type uint64;
          description
            "octets";
        }
        leaf oversize-frames {
          type uint64;
          description
            "oversize frames";
        }
        leaf undersize-frames {
          type uint64;
          description
            "undersize frames";
        }
      }
    }
    container PON_ONU_STATISTICS_ACCUMULATING_ONU_ETHERNET_FRAME_PM_DOWNSTREAM {
      description
        "PON_ONU_STATISTICS_ACCUMULATING_ONU_ETHERNET_FRAME_PM_DOWNSTREAM table in CounterDB.";
      config false;
      list PON_ONU_STATISTICS_ACCUMULATING_ONU_ETHERNET_FRAME_PM_DOWNSTREAM_LIST {
        key "onu-name onu-id";
        description
          "GPON: Downstream MAC Bridge Service Profile statistics reported by ONU through OMCI.
           CounterDB key: PON_ONU_STATISTICS_ACCUMULATING_ONU_ETHERNET_FRAME_PM_DOWNSTREAM|<onu-name>|<onu-id>.";
        leaf onu-name {
          type leafref {
            path "/sp:sonic-pon/sp:PON_ONU_STATE/sp:PON_ONU_STATE_LIST/sp:onu-name";
          }
          description
            "References PON_ONU_STATE_LIST.";
        }
        leaf onu-id {
          type uint16;
          description
            "Performance management ME ID.";
        }
        leaf broadcast-packets {
          type uint64;
          description
            "broadcast packets";
        }
        leaf crc-errored-packets {
          type uint64;
          description
            "crc errored packets";
        }
        leaf drop-events {
          type uint64;
          description
            "drop events";
        }
        leaf interval-end-time {
          type uint64;
          description
            "interval end time";
        }
        leaf multicast-packets {
          type uint64;
          description
            "multicast packets";
        }
        leaf octets {
          type uint64;
          description
            "octets";
        }
        leaf oversize-packets {
          type uint64;
          description
            "oversize packets";
        }
        leaf packets {
          type uint64;
          description
            "packets";
        }
        leaf packets-1024-to-1518-octets {
          type uint64;
          description
            "packets 1024 to 1518 octets";
        }
        leaf packets-128-to-255-octets {
          type uint64;
          description
            "packets 128 to 255 octets";
        }
        leaf packets-256-to-511-octets {
          type uint64;
          description
            "packets 256 to 511 octets";
        }
        leaf packets-512-to-1023-octets {
          type uint64;
          description
            "packets 512 to 1023 octets";
        }
        leaf packets-64-octets {
          type uint64;
          description
            "packets 64 octets";
        }
        leaf packets-65-to-127-octets {
          type uint64;
          description
            "packets 65 to 127 octets";
        }
        leaf threshold-data-1-2-id {
          type omci-types:omci-uint16;
          description
            "threshold data 1/2 id";
        }
        leaf undersize-packets {
          type uint64;
          description
            "undersize packets";
        }
      }
    }
    container PON_ONU_STATISTICS_ACCUMULATING_ONU_ETHERNET_FRAME_PM_UPSTREAM {
      description
        "PON_ONU_STATISTICS_ACCUMULATING_ONU_ETHERNET_FRAME_PM_UPSTREAM table in CounterDB.";
      config false;
      list PON_ONU_STATISTICS_ACCUMULATING_ONU_ETHERNET_FRAME_PM_UPSTREAM_LIST {
        key "onu-name onu-id";
        description
          "GPON: Upstream MAC Bridge Service Profile statistics reported by ONU through OMCI.
           CounterDB key: PON_ONU_STATISTICS_ACCUMULATING_ONU_ETHERNET_FRAME_PM_UPSTREAM|<onu-name>|<onu-id>.";
        leaf onu-name {
          type leafref {
            path "/sp:sonic-pon/sp:PON_ONU_STATE/sp:PON_ONU_STATE_LIST/sp:onu-name";
          }
          description
            "References PON_ONU_STATE_LIST.";
        }
        leaf onu-id {
          type uint16;
          description
            "Performance management ME ID.";
        }
        leaf broadcast-packets {
          type uint64;
          description
            "broadcast packets";
        }
        leaf crc-errored-packets {
          type uint64;
          description
            "crc errored packets";
        }
        leaf drop-events {
          type uint64;
          description
            "drop events";
        }
        leaf interval-end-time {
          type uint64;
          description
            "interval end time";
        }
        leaf multicast-packets {
          type uint64;
          description
            "multicast packets";
        }
        leaf octets {
          type uint64;
          description
            "octets";
        }
        leaf oversize-packets {
          type uint64;
          description
            "oversize packets";
        }
        leaf packets {
          type uint64;
          description
            "packets";
        }
        leaf packets-1024-to-1518-octets {
          type uint64;
          description
            "packets 1024 to 1518 octets";
        }
        leaf packets-128-to-255-octets {
          type uint64;
          description
            "packets 128 to 255 octets";
        }
        leaf packets-256-to-511-octets {
          type uint64;
          description
            "packets 256 to 511 octets";
        }
        leaf packets-512-to-1023-octets {
          type uint64;
          description
            "packets 512 to 1023 octets";
        }
        leaf packets-64-octets {
          type uint64;
          description
            "packets 64 octets";
        }
        leaf packets-65-to-127-octets {
          type uint64;
          description
            "packets 65 to 127 octets";
        }
        leaf threshold-data-1-2-id {
          type omci-types:omci-uint16;
          description
            "threshold data 1/2 id";
        }
        leaf undersize-packets {
          type uint64;
          description
            "undersize packets";
        }
      }
    }
    container PON_ONU_STATISTICS_ACCUMULATING_ONU_ETHERNET_PM {
      description
        "PON_ONU_STATISTICS_ACCUMULATING_ONU_ETHERNET_PM table in CounterDB.";
      config false;
      list PON_ONU_STATISTICS_ACCUMULATING_ONU_ETHERNET_PM_LIST {
        key "onu-name onu-id";
        description
          "GPON: Ethernet UNI port statistics reported by ONU through OMCI.
           CounterDB key: PON_ONU_STATISTICS_ACCUMULATING_ONU_ETHERNET_PM|<onu-name>|<onu-id>.";
        leaf onu-name {
          type leafref {
            path "/sp:sonic-pon/sp:PON_ONU_STATE/sp:PON_ONU_STATE_LIST/sp:onu-name";
          }
          description
            "References PON_ONU_STATE_LIST.";
        }
        leaf onu-id {
          type uint16;
          description
            "Performance management ME ID.";
        }
        leaf alignment-error-counter {
          type uint64;
          description
            "alignment error counter";
        }
        leaf buffer-overflows-on-receive {
          type uint64;
          description
            "buffer overflows on receive";
        }
        leaf buffer-overflows-on-transmit {
          type uint64;
          description
            "buffer overflows on transmit";
        }
        leaf carrier-sense-error-counter {
          type uint64;
          description
            "carrier sense error counter";
        }
        leaf deferred-transmission-counter {
          type uint64;
          description
            "deferred transmission counter";
        }
        leaf excessive-collision-counter {
          type uint64;
          description
            "excessive collision counter";
        }
        leaf fcs-errors {
          type uint64;
          description
            "fcs errors";
        }
        leaf frames-too-long {
          type uint64;
          description
            "frames too long";
        }
        leaf internal-mac-receive-error-counter {
          type uint64;
          description
            "internal mac receive error counter";
        }
        leaf internal-mac-transmit-error-counter {
          type uint64;
          description
            "internal mac transmit error counter";
        }
        leaf interval-end-time {
          type uint64;
          description
            "interval end time";
        }
        leaf late-collision-counter {
          type uint64;
          description
            "late collision counter";
        }
        leaf multiple-collisions-frame-counter {
          type uint64;
          description
            "multiple collisions frame counter";
        }
        leaf single-collision-frame-counter {
          type uint64;
          description
            "single collision frame counter";
        }
        leaf sqe-counter {
          type uint64;
          description
            "sqe counter";
        }
        leaf threshold-data-1-2-id {
          type omci-types:omci-uint16;
          description
            "threshold data 1/2 id";
        }
      }
    }
    container PON_ONU_STATISTICS_ACCUMULATING_ONU_ETHERNET_PM3 {
      description
        "PON_ONU_STATISTICS_ACCUMULATING_ONU_ETHERNET_PM3 table in CounterDB.";
      config false;
      list PON_ONU_STATISTICS_ACCUMULATING_ONU_ETHERNET_PM3_LIST {
        key "onu-name onu-id";
        description
          "GPON: Counters associated with ethernet messages.
           CounterDB key: PON_ONU_STATISTICS_ACCUMULATING_ONU_ETHERNET_PM3|<onu-name>|<onu-id>.";
        leaf onu-name {
          type leafref {
            path "/sp:sonic-pon/sp:PON_ONU_STATE/sp:PON_ONU_STATE_LIST/sp:onu-name";
          }
          description
            "References PON_ONU_STATE_LIST.";
        }
        leaf onu-id {
          type uint16;
          description
            "Performance management ME ID.";
        }
        leaf broadcast-packets {
          type uint64;
          description
            "Total number of received good packets directed to the broadcast address. This does not include multicast packets";
        }
        leaf drop-events {
          type uint64;
          description
            "Total number of events in which packets were dropped due to a lack of resources";
        }
        leaf fragments {
          type uint64;
          description
            "Total number of packets received that were less than 64 octets long";
        }
        leaf interval-end-time {
          type uint64;
          description
            "Identifies the most recently finished 15 min interval";
        }
        leaf jabbers {
          type uint64;
          description
            "Total number of packets received that were longer than 1518 octets";
        }
        leaf multicast-packets {
          type uint64;
          description
            "Total number of received good packets directed to a multicast address. This does not include broadcast packets";
        }
        leaf octets {
          type uint64;
          description
            "Total number of octets received from the CPE, including those in bad packets";
        }
        leaf packets {
          type uint64;
          description
            "Total number of packets received, including bad packets, broadcast packets and multicast packets";
        }
        leaf packets-64-octets {
          type uint64;
          description
            "Total number of received packets (including bad packets) that were 64 octets long";
        }
        leaf packets-65-to-127-octets {
          type uint64;
          description
            "Total number of received packets (including bad packets) that were 65 to 127 octets long";
        }
        leaf packets-128-to-255-octets {
          type uint64;
          description
            "Total number of received packets (including bad packets) that were 128 to 255 octets long";
        }
        leaf packets-256-to-511-octets {
          type uint64;
          description
            "Total number of received packets (including bad packets) that were 256 to 511 octets long";
        }
        leaf packets-512-to-1023-octets {
          type uint64;
          description
            "Total number of received packets (including bad packets) that were 512 to 1023 octets long";
        }
        leaf packets-1024-to-1518-octets {
          type uint64;
          description
            "Total number of received packets (including bad packets) that were 1024 to 1518 octets long";
        }
        leaf threshold-data-1-2-id {
          type omci-types:omci-uint16;
          description
            "Points to an instance of the threshold data 1 ME that contains PM threshold values";
        }
        leaf undersize-packets {
          type uint64;
          description
            "Counts the number of frames discarded due to PPPoE filtering";
        }
      }
    }
    container PON_ONU_STATISTICS_ACCUMULATING_ONU_GAL_ETHERNET_PM {
      description
        "PON_ONU_STATISTICS_ACCUMULATING_ONU_GAL_ETHERNET_PM table in CounterDB.";
      config false;
      list PON_ONU_STATISTICS_ACCUMULATING_ONU_GAL_ETHERNET_PM_LIST {
        key "onu-name onu-id";
        description
          "GPON: Counters associated with gal ethernet messages.
           CounterDB key: PON_ONU_STATISTICS_ACCUMULATING_ONU_GAL_ETHERNET_PM|<onu-name>|<onu-id>.";
        leaf onu-name {
          type leafref {
            path "/sp:sonic-pon/sp:PON_ONU_STATE/sp:PON_ONU_STATE_LIST/sp:onu-name";
          }
          description
            "References PON_ONU_STATE_LIST.";
        }
        leaf onu-id {
          type uint16;
          description
            "Performance management ME ID.";
        }
        leaf discarded-downstream-frames {
          type uint64;
          description
            "Counts the number of downstream GEM frames discarded for any reason";
        }
        leaf discarded-upstream-frames {
          type uint64;
          description
            "Counts the number of upstream frames discarded prior to GEM encapsulation (due to congestion)";
        }
        leaf interval-end-time {
          type uint64;
          description
            "Identifies the most recently finished 15 min interval";
        }
        leaf threshold-data-1-2-id {
          type omci-types:omci-uint16;
          description
            "Points to an instance of the threshold data 1 ME that contains PM threshold values";
        }
      }
    }
    container PON_ONU_STATISTICS_ACCUMULATING_ONU_GEM_PORT_NETWORK_CTP_PM {
      description
        "PON_ONU_STATISTICS_ACCUMULATING_ONU_GEM_PORT_NETWORK_CTP_PM table in CounterDB.";
      config false;
      list PON_ONU_STATISTICS_ACCUMULATING_ONU_GEM_PORT_NETWORK_CTP_PM_LIST {
        key "onu-name onu-id";
        description
          "GPON: Counters associated with gem port network ctp messages.
           CounterDB key: PON_ONU_STATISTICS_ACCUMULATING_ONU_GEM_PORT_NETWORK_CTP_PM|<onu-name>|<onu-id>.";
        leaf onu-name {
          type leafref {
            path "/sp:sonic-pon/sp:PON_ONU_STATE/sp:PON_ONU_STATE_LIST/sp:onu-name";
          }
          description
            "References PON_ONU_STATE_LIST.";
        }
        leaf onu-id {
          type uint16;
          description
            "Performance management ME ID.";
        }
        leaf encryption-key-errors {
          type uint64;
          description
            "Counts GEM frames with erroneous encryption key indexes. If the GEM port is not encrypted,
             this attribute counts any frame with a key index not equal to 0. If the GEM port is encrypted,
             this attribute counts any frame whose key index specifies a key that is not known to the ONU.
            ";
        }
        leaf interval-end-time {
          type uint64;
          description
            "Identifies the most recently finished 15 min interval";
        }
        leaf received-gem-frames {
          type uint64;
          description
            "Counts GEM frames received correctly on the monitored GEM port. A correctly received GEM frame
             is one that does not contain uncorrectable errors and has a valid header error check (HEC).
            ";
        }
        leaf received-payload-bytes {
          type uint64;
          description
            "Counts user payload bytes received on the monitored GEM port";
        }
        leaf threshold-data-1-2-id {
          type omci-types:omci-uint16;
          description
            "Points to an instance of the threshold data 1 ME that contains PM threshold values";
        }
        leaf transmitted-gem-frames {
          type uint64;
          description
            "Counts GEM frames transmitted on the monitored GEM port";
        }
        leaf transmitted-payload-bytes {
          type uint64;
          description
            "Counts user payload bytes transmitted on the monitored GEM port";
        }
      }
    }
    container PON_ONU_STATISTICS_ACCUMULATING_ONU_IP_HOST_PERF_MON_HIST_DATA {
      description
        "PON_ONU_STATISTICS_ACCUMULATING_ONU_IP_HOST_PERF_MON_HIST_DATA table in CounterDB.";
      config false;
      list PON_ONU_STATISTICS_ACCUMULATING_ONU_IP_HOST_PERF_MON_HIST_DATA_LIST {
        key "onu-name onu-id";
        description
          "ME collects PM data related to an IP host.
           CounterDB key: PON_ONU_STATISTICS_ACCUMULATING_ONU_IP_HOST_PERF_MON_HIST_DATA|<onu-name>|<onu-id>.";
        leaf onu-name {
          type leafref {
            path "/sp:sonic-pon/sp:PON_ONU_STATE/sp:PON_ONU_STATE_LIST/sp:onu-name";
          }
          description
            "References PON_ONU_STATE_LIST.";
        }
        leaf onu-id {
          type uint16;
          description
            "ME Identifier for this IP host.";
        }
        leaf dns-errors {
          type uint64;
          description
            "Counts DNS errors received.";
        }
        leaf dhcp-timeouts {
          type uint64;
          description
            "Counts DHCP timeouts received.";
        }
        leaf icmp-errors {
          type uint64;
          description
            "Counts ICMP errors received.";
        }
        leaf internal-error {
          type uint64;
          description
            "Incremented whenever the ONU encounters an internal error condition such as a driver interface failure in the IP stack.";
        }
        leaf interval-end-time {
          type uint64;
          description
            "Identifies the most recently finished 15 min interval.";
        }
        leaf ip-address-conflict {
          type uint64;
          description
            "Incremented whenever the ONU detects a conflicting IP address on the network.
             A conflicting IP address is one that has the same value as the one curently assigned to the ONU.
            ";
        }
        leaf out-of-memory {
          type uint64;
          description
            "Incremented whenever the ONU encounters an out of memory condition in the IP stack.";
        }
        leaf threshold-data-1-2-id {
          type omci-types:omci-uint16;
          description
            "Points to an instance of the threshold data 1 ME that contains PM threshold values.";
        }
      }
    }
    container PON_ONU_STATISTICS_ACCUMULATING_ONU_OPERATIONAL_PM {
      description
        "PON_ONU_STATISTICS_ACCUMULATING_ONU_OPERATIONAL_PM table in CounterDB.";
      config false;
      list PON_ONU_STATISTICS_ACCUMULATING_ONU_OPERATIONAL_PM_LIST {
        key "onu-name onu-id";
        description
          "GPON: Counters associated with operational messages.
           CounterDB key: PON_ONU_STATISTICS_ACCUMULATING_ONU_OPERATIONAL_PM|<onu-name>|<onu-id>.";
        leaf onu-name {
          type leafref {
            path "/sp:sonic-pon/sp:PON_ONU_STATE/sp:PON_ONU_STATE_LIST/sp:onu-name";
          }
          description
            "References PON_ONU_STATE_LIST.";
        }
        leaf onu-id {
          type uint16;
          description
            "Performance management ME ID.";
        }
        leaf cpu-percent-utilization {
          type uint64;
          description
            "Maximum system CPU utilization (high water mark) during the measurement interval";
        }
        leaf errors-in-operations {
          type uint64;
          description
            "Count of the number of detected errors in operations, not due to a software error";
        }
        leaf flash-size-available {
          type uint64;
          description
            "Minimum FLASH size available during the measurement interval";
        }
        leaf flash-utilization {
          type uint64;
          description
            "Maximum FLASH size utilized during the measurement interval";
        }
        leaf interval-end-time {
          type uint64;
          description
            "Identifies the most recently finished 15 min interval.";
        }
        leaf ram-size-available {
          type uint64;
          description
            "Minimum RAM size available during the measurement interval";
        }
        leaf ram-utilization {
          type uint64;
          description
            "Maximum RAM size utilized during the measurement interval";
        }
        leaf software-errors {
          type uint64;
          description
            "Count of the number of software errors detected";
        }
        leaf threshold-data-1-2-id {
          type omci-types:omci-uint16;
          description
            "Points to an instance of the threshold data 1 ME that contains PM threshold values.";
        }
        leaf temperature-sensor-description {
          type uint64;
          description
            "A table of temperature sensor descriptions that includes the physical location on the ONU or the component being measured";
        }
        leaf temperature-sensor-value {
          type uint64;
          description
            "A table of temperature sensor values that specifies the average temperature of the ONU temperature sensor(s) during the measurement interval";
        }
      }
    }
    container PON_ONU_STATISTICS_ACCUMULATING_ONU_MAC_BRIDGE_PORT_PM {
      description
        "PON_ONU_STATISTICS_ACCUMULATING_ONU_MAC_BRIDGE_PORT_PM table in CounterDB.";
      config false;
      list PON_ONU_STATISTICS_ACCUMULATING_ONU_MAC_BRIDGE_PORT_PM_LIST {
        key "onu-name onu-id";
        description
          "GPON: ME collects PM data related to a mac bridge port.
           CounterDB key: PON_ONU_STATISTICS_ACCUMULATING_ONU_MAC_BRIDGE_PORT_PM|<onu-name>|<onu-id>.";
        leaf onu-name {
          type leafref {
            path "/sp:sonic-pon/sp:PON_ONU_STATE/sp:PON_ONU_STATE_LIST/sp:onu-name";
          }
          description
            "References PON_ONU_STATE_LIST.";
        }
        leaf onu-id {
          type uint16;
          description
            "ME Identifier for this mac bridge port.";
        }
        leaf delay-exceeded-discard-counter {
          type uint64;
          description
            "Counts frames discarded on this port because transmission was delayed";
        }
        leaf forwarded-frame-counter {
          type uint64;
          description
            "Counts frames transmitted successfully on this port";
        }
        leaf interval-end-time {
          type uint64;
          description
            "Identifies the most recently finished 15 min interval";
        }
        leaf mtu-exceeded-discard-counter {
          type uint64;
          description
            "Counts frames discarded on this port because the MTU was exceeded";
        }
        leaf received-and-discarded-counter {
          type uint64;
          description
            "Counts frames received on this port that were discarded due to errors";
        }
        leaf received-frame-counter {
          type uint64;
          description
            "Counts frames received on this port";
        }
        leaf threshold-data-1-2-id {
          type omci-types:omci-uint16;
          description
            "Points to an instance of the threshold data 1 ME that contains PM threshold values";
        }
      }
    }
    container PON_ONU_STATISTICS_ACCUMULATING_ONU_RS232_RS485_PERF_MON_HIST_DATA {
      description
        "PON_ONU_STATISTICS_ACCUMULATING_ONU_RS232_RS485_PERF_MON_HIST_DATA table in CounterDB.";
      config false;
      list PON_ONU_STATISTICS_ACCUMULATING_ONU_RS232_RS485_PERF_MON_HIST_DATA_LIST {
        key "onu-name onu-id";
        description
          "ME collects PM data for a RS232/RS485 interface.
           CounterDB key: PON_ONU_STATISTICS_ACCUMULATING_ONU_RS232_RS485_PERF_MON_HIST_DATA|<onu-name>|<onu-id>.";
        leaf onu-name {
          type leafref {
            path "/sp:sonic-pon/sp:PON_ONU_STATE/sp:PON_ONU_STATE_LIST/sp:onu-name";
          }
          description
            "References PON_ONU_STATE_LIST.";
        }
        leaf onu-id {
          type uint16;
          description
            "ME Identifier for this RS232/RS485 interface.";
        }
        leaf incoming-bytes-from-chip {
          type uint64;
          description
            "Counts the bytes received on the RS232/RS485 chipset.";
        }
        leaf incoming-bytes-from-pon {
          type uint64;
          description
            "Counts the bytes received on the PON port.";
        }
        leaf interval-end-time {
          type uint64;
          description
            "Identifies the most recently finished 15 min interval.";
        }
        leaf outgoing-bytes-from-chip {
          type uint64;
          description
            "Counts the bytes transmitted on the RS232/RS485 chipset.";
        }
        leaf outgoing-bytes-from-pon {
          type uint64;
          description
            "Counts the bytes transmitted on the PON port.";
        }
        leaf threshold-data-1-2-id {
          type omci-types:omci-uint16;
          description
            "Points to an instance of the threshold data 1 ME that contains PM threshold values.";
        }
      }
    }
    container PON_ONU_STATISTICS_ACCUMULATING_ONU_TCP_UDP_PERF_MON_HIST_DATA {
      description
        "PON_ONU_STATISTICS_ACCUMULATING_ONU_TCP_UDP_PERF_MON_HIST_DATA table in CounterDB.";
      config false;
      list PON_ONU_STATISTICS_ACCUMULATING_ONU_TCP_UDP_PERF_MON_HIST_DATA_LIST {
        key "onu-name onu-id";
        description
          "ME collects PM data related to a TCP or UDP port.
           CounterDB key: PON_ONU_STATISTICS_ACCUMULATING_ONU_TCP_UDP_PERF_MON_HIST_DATA|<onu-name>|<onu-id>.";
        leaf onu-name {
          type leafref {
            path "/sp:sonic-pon/sp:PON_ONU_STATE/sp:PON_ONU_STATE_LIST/sp:onu-name";
          }
          description
            "References PON_ONU_STATE_LIST.";
        }
        leaf onu-id {
          type uint16;
          description
            "ME Identifier for this TCP or UDP port.";
        }
        leaf accept-failed {
          type uint64;
          description
            "Incremented when an attempt to accept a connection on a port fails.";
        }
        leaf bind-failed {
          type uint64;
          description
            "Incremented when an attempt by a service to bind to a port fails.";
        }
        leaf interval-end-time {
          type uint64;
          description
            "Identifies the most recently finished 15 min interval.";
        }
        leaf listen-failed {
          type uint64;
          description
            "Incremented when an attempt by a service to listen for a request on a port fails.";
        }
        leaf select-failed {
          type uint64;
          description
            "Incremented when an attempt to perform a select on a group of ports fails.";
        }
        leaf socket-failed {
          type uint64;
          description
            "Incremented when an attempt to create a socket associated with a port fails.";
        }
        leaf threshold-data-1-2-id {
          type omci-types:omci-uint16;
          description
            "Points to an instance of the threshold data 1 ME that contains PM threshold values.";
        }
      }
    }
    container PON_ONU_STATISTICS_ACCUMULATING_ONU_XG_PON_DOWNSTREAM_MGMT_PM {
      description
        "PON_ONU_STATISTICS_ACCUMULATING_ONU_XG_PON_DOWNSTREAM_MGMT_PM table in CounterDB.";
      config false;
      list PON_ONU_STATISTICS_ACCUMULATING_ONU_XG_PON_DOWNSTREAM_MGMT_PM_LIST {
        key "onu-name onu-id";
        description
          "GPON: Counters associated with downstream PLOAM and OMCI messages.
           CounterDB key: PON_ONU_STATISTICS_ACCUMULATING_ONU_XG_PON_DOWNSTREAM_MGMT_PM|<onu-name>|<onu-id>.";
        leaf onu-name {
          type leafref {
            path "/sp:sonic-pon/sp:PON_ONU_STATE/sp:PON_ONU_STATE_LIST/sp:onu-name";
          }
          description
            "References PON_ONU_STATE_LIST.";
        }
        leaf onu-id {
          type uint16;
          description
            "Performance management ME ID.";
        }
        leaf interval-end-time {
          type uint64;
          description
            "Identifies the most recently finished 15 min interval.";
        }
        leaf threshold-data-1-2-id {
          type omci-types:omci-uint16;
          description
            "Points to an instance of the threshold data 1 ME that contains PM threshold values.";
        }
        leaf ploam-mic-error-count {
          type uint64;
          description
            "Counts MIC errors detected in downstream PLOAM messages, either directed to this ONU or broadcast to all ONUs";
        }
        leaf downstream-ploam-message-count {
          type uint64;
          description
            "Counts PLOAM messages received, either directed to this ONU or broadcast to all ONUs";
        }
        leaf profile-messages-received {
          type uint64;
          description
            "Counts the number of profile messages received, either directed to this ONU or broadcast to all ONUs.";
        }
        leaf ranging-time-messages-received {
          type uint64;
          description
            "Counts the number of ranging_time messages received, either directed to this ONU or broadcast to all ONUs.";
        }
        leaf deactivate-onu-id-messages-received {
          type uint64;
          description
            "Counts the number of deactivate_ONU-ID messages received, either directed to this ONU or broadcast to all ONUs";
        }
        leaf disable-serial-number-messages-received {
          type uint64;
          description
            "Counts the number of disable_serial_number messages received, whose serial number specified this ONU";
        }
        leaf request-registration-messages-received {
          type uint64;
          description
            "Counts the number of request_registration messages received";
        }
        leaf assign-alloc-id-messages-received {
          type uint64;
          description
            "Counts the number of assign_alloc-ID messages received";
        }
        leaf key-control-messages-received {
          type uint64;
          description
            "Counts the number of key_control messages received";
        }
        leaf sleep-allow-messages-received {
          type uint64;
          description
            "Counts the number of sleep_allow messages received";
        }
        leaf baseline-omci-messages-received-count {
          type uint64;
          description
            "Counts the number of OMCI messages received in the baseline message format";
        }
        leaf extended-omci-messages-received-count {
          type uint64;
          description
            "Counts the number of OMCI messages received in the extended message format";
        }
        leaf assign-onu-id-omci-messages-received {
          type uint64;
          description
            "Counts the number of assign_ONU-ID messages received since the last reboot";
        }
        leaf omci-mic-error-count {
          type uint64;
          description
            "Counts the number of MIC errors detected in OMCI messages directed to this ONU";
        }
      }
    }
    container PON_ONU_STATISTICS_ACCUMULATING_ONU_XG_PON_UPSTREAM_MGMT_PM {
      description
        "PON_ONU_STATISTICS_ACCUMULATING_ONU_XG_PON_UPSTREAM_MGMT_PM table in CounterDB.";
      config false;
      list PON_ONU_STATISTICS_ACCUMULATING_ONU_XG_PON_UPSTREAM_MGMT_PM_LIST {
        key "onu-name onu-id";
        description
          "GPON: Counters associated with upstream PLOAM and OMCI messages.
           CounterDB key: PON_ONU_STATISTICS_ACCUMULATING_ONU_XG_PON_UPSTREAM_MGMT_PM|<onu-name>|<onu-id>.";
        leaf onu-name {
          type leafref {
            path "/sp:sonic-pon/sp:PON_ONU_STATE/sp:PON_ONU_STATE_LIST/sp:onu-name";
          }
          description
            "References PON_ONU_STATE_LIST.";
        }
        leaf onu-id {
          type uint16;
          description
            "Performance management ME ID.";
        }
        leaf interval-end-time {
          type uint64;
          description
            "Identifies the most recently finished 15 min interval.";
        }
        leaf threshold-data-1-2-id {
          type omci-types:omci-uint16;
          description
            "Points to an instance of the threshold data 1 ME that contains PM threshold values.";
        }
        leaf upstream-ploam-message-count {
          type uint64;
          description
            "Counts PLOAM messages transmitted upstream, excluding acknowledge messages";
        }
        leaf serial-number-message-count {
          type uint64;
          description
            "Counts Serial_number_ONU PLOAM messages transmitted";
        }
        leaf registration-message-count {
          type uint64;
          description
            "Counts registration PLOAM messages transmitted";
        }
        leaf key-report-message-count {
          type uint64;
          description
            "Counts key_report PLOAM messages transmitted";
        }
        leaf acknowledge-message-count {
          type uint64;
          description
            "Counts acknowledge PLOAM messages transmitted. It includes all forms of acknowledgement,
             including those transmitted in response to a PLOAMu grant when the ONU has nothing to send.
            ";
        }
        leaf sleep-request-message-count {
          type uint64;
          description
            "Counts sleep_request PLOAM messages transmitted";
        }
      }
    }
    container PON_ONU_STATISTICS_STREAMING_ONU_ETHERNET_PM {
      description
        "PON_ONU_STATISTICS_STREAMING_ONU_ETHERNET_PM table in StateDB.";
      config false;
      list PON_ONU_STATISTICS_STREAMING_ONU_ETHERNET_PM_LIST {
        key "onu-name onu-id";
        description
          "GPON: Ethernet UNI port statistics reported by ONU through OMCI.
           StateDB key: PON_ONU_STATISTICS_STREAMING_ONU_ETHERNET_PM|<onu-name>|<onu-id>.";
        leaf onu-name {
          type leafref {
            path "/sp:sonic-pon/sp:PON_ONU_STATE/sp:PON_ONU_STATE_LIST/sp:onu-name";
          }
          description
            "References PON_ONU_STATE_LIST.";
        }
        leaf onu-id {
          type uint16;
          description
            "Performance management ME ID.";
        }
        leaf alignment-error-counter {
          type uint64;
          description
            "alignment error counter";
        }
        leaf buffer-overflows-on-receive {
          type uint64;
          description
            "buffer overflows on receive";
        }
        leaf buffer-overflows-on-transmit {
          type uint64;
          description
            "buffer overflows on transmit";
        }
        leaf carrier-sense-error-counter {
          type uint64;
          description
            "carrier sense error counter";
        }
        leaf deferred-transmission-counter {
          type uint64;
          description
            "deferred transmission counter";
        }
        leaf excessive-collision-counter {
          type uint64;
          description
            "excessive collision counter";
        }
        leaf fcs-errors {
          type uint64;
          description
            "fcs errors";
        }
        leaf frames-too-long {
          type uint64;
          description
            "frames too long";
        }
        leaf internal-mac-receive-error-counter {
          type uint64;
          description
            "internal mac receive error counter";
        }
        leaf internal-mac-transmit-error-counter {
          type uint64;
          description
            "internal mac transmit error counter";
        }
        leaf interval-end-time {
          type uint64;
          description
            "interval end time";
        }
        leaf late-collision-counter {
          type uint64;
          description
            "late collision counter";
        }
        leaf multiple-collisions-frame-counter {
          type uint64;
          description
            "multiple collisions frame counter";
        }
        leaf single-collision-frame-counter {
          type uint64;
          description
            "single collision frame counter";
        }
        leaf sqe-counter {
          type uint64;
          description
            "sqe counter";
        }
        leaf threshold-data-1-2-id {
          type omci-types:omci-uint16;
          description
            "threshold data 1/2 id";
        }
      }
    }
    container PON_ONU_STATISTICS_STREAMING_ONU_ETHERNET_FRAME_PM_DOWNSTREAM {
      description
        "PON_ONU_STATISTICS_STREAMING_ONU_ETHERNET_FRAME_PM_DOWNSTREAM table in StateDB.";
      config false;
      list PON_ONU_STATISTICS_STREAMING_ONU_ETHERNET_FRAME_PM_DOWNSTREAM_LIST {
        key "onu-name onu-id";
        description
          "GPON: Downstream MAC Bridge Service Profile statistics reported by ONU through OMCI.
           StateDB key: PON_ONU_STATISTICS_STREAMING_ONU_ETHERNET_FRAME_PM_DOWNSTREAM|<onu-name>|<onu-id>.";
        leaf onu-name {
          type leafref {
            path "/sp:sonic-pon/sp:PON_ONU_STATE/sp:PON_ONU_STATE_LIST/sp:onu-name";
          }
          description
            "References PON_ONU_STATE_LIST.";
        }
        leaf onu-id {
          type uint16;
          description
            "Performance management ME ID.";
        }
        leaf broadcast-packets {
          type uint64;
          description
            "broadcast packets";
        }
        leaf crc-errored-packets {
          type uint64;
          description
            "crc errored packets";
        }
        leaf drop-events {
          type uint64;
          description
            "drop events";
        }
        leaf interval-end-time {
          type uint64;
          description
            "interval end time";
        }
        leaf multicast-packets {
          type uint64;
          description
            "multicast packets";
        }
        leaf octets {
          type uint64;
          description
            "octets";
        }
        leaf oversize-packets {
          type uint64;
          description
            "oversize packets";
        }
        leaf packets {
          type uint64;
          description
            "packets";
        }
        leaf packets-1024-to-1518-octets {
          type uint64;
          description
            "packets 1024 to 1518 octets";
        }
        leaf packets-128-to-255-octets {
          type uint64;
          description
            "packets 128 to 255 octets";
        }
        leaf packets-256-to-511-octets {
          type uint64;
          description
            "packets 256 to 511 octets";
        }
        leaf packets-512-to-1023-octets {
          type uint64;
          description
            "packets 512 to 1023 octets";
        }
        leaf packets-64-octets {
          type uint64;
          description
            "packets 64 octets";
        }
        leaf packets-65-to-127-octets {
          type uint64;
          description
            "packets 65 to 127 octets";
        }
        leaf threshold-data-1-2-id {
          type omci-types:omci-uint16;
          description
            "threshold data 1/2 id";
        }
        leaf undersize-packets {
          type uint64;
          description
            "undersize packets";
        }
      }
    }
    container PON_ONU_STATISTICS_STREAMING_ONU_ETHERNET_FRAME_PM_UPSTREAM {
      description
        "PON_ONU_STATISTICS_STREAMING_ONU_ETHERNET_FRAME_PM_UPSTREAM table in StateDB.";
      config false;
      list PON_ONU_STATISTICS_STREAMING_ONU_ETHERNET_FRAME_PM_UPSTREAM_LIST {
        key "onu-name onu-id";
        description
          "GPON: Upstream MAC Bridge Service Profile statistics reported by ONU through OMCI.
           StateDB key: PON_ONU_STATISTICS_STREAMING_ONU_ETHERNET_FRAME_PM_UPSTREAM|<onu-name>|<onu-id>.";
        leaf onu-name {
          type leafref {
            path "/sp:sonic-pon/sp:PON_ONU_STATE/sp:PON_ONU_STATE_LIST/sp:onu-name";
          }
          description
            "References PON_ONU_STATE_LIST.";
        }
        leaf onu-id {
          type uint16;
          description
            "Performance management ME ID.";
        }
        leaf broadcast-packets {
          type uint64;
          description
            "broadcast packets";
        }
        leaf crc-errored-packets {
          type uint64;
          description
            "crc errored packets";
        }
        leaf drop-events {
          type uint64;
          description
            "drop events";
        }
        leaf interval-end-time {
          type uint64;
          description
            "interval end time";
        }
        leaf multicast-packets {
          type uint64;
          description
            "multicast packets";
        }
        leaf octets {
          type uint64;
          description
            "octets";
        }
        leaf oversize-packets {
          type uint64;
          description
            "oversize packets";
        }
        leaf packets {
          type uint64;
          description
            "packets";
        }
        leaf packets-1024-to-1518-octets {
          type uint64;
          description
            "packets 1024 to 1518 octets";
        }
        leaf packets-128-to-255-octets {
          type uint64;
          description
            "packets 128 to 255 octets";
        }
        leaf packets-256-to-511-octets {
          type uint64;
          description
            "packets 256 to 511 octets";
        }
        leaf packets-512-to-1023-octets {
          type uint64;
          description
            "packets 512 to 1023 octets";
        }
        leaf packets-64-octets {
          type uint64;
          description
            "packets 64 octets";
        }
        leaf packets-65-to-127-octets {
          type uint64;
          description
            "packets 65 to 127 octets";
        }
        leaf threshold-data-1-2-id {
          type omci-types:omci-uint16;
          description
            "threshold data 1/2 id";
        }
        leaf undersize-packets {
          type uint64;
          description
            "undersize packets";
        }
      }
    }
    container PON_ONU_STATISTICS_STREAMING_ONU_RS232_RS485_PERF_MON_HIST_DATA {
      description
        "PON_ONU_STATISTICS_STREAMING_ONU_RS232_RS485_PERF_MON_HIST_DATA table in StateDB.";
      config false;
      list PON_ONU_STATISTICS_STREAMING_ONU_RS232_RS485_PERF_MON_HIST_DATA_LIST {
        key "onu-name onu-id";
        description
          "ME collects PM data for a RS232/RS485 interface.
           StateDB key: PON_ONU_STATISTICS_STREAMING_ONU_RS232_RS485_PERF_MON_HIST_DATA|<onu-name>|<onu-id>.";
        leaf onu-name {
          type leafref {
            path "/sp:sonic-pon/sp:PON_ONU_STATE/sp:PON_ONU_STATE_LIST/sp:onu-name";
          }
          description
            "References PON_ONU_STATE_LIST.";
        }
        leaf onu-id {
          type uint16;
          description
            "ME Identifier for this RS232/RS485 interface.";
        }
        leaf incoming-bytes-from-chip {
          type uint64;
          description
            "Counts the bytes received on the RS232/RS485 chipset.";
        }
        leaf incoming-bytes-from-pon {
          type uint64;
          description
            "Counts the bytes received on the PON port.";
        }
        leaf interval-end-time {
          type uint64;
          description
            "Identifies the most recently finished 15 min interval.";
        }
        leaf outgoing-bytes-from-chip {
          type uint64;
          description
            "Counts the bytes transmitted on the RS232/RS485 chipset.";
        }
        leaf outgoing-bytes-from-pon {
          type uint64;
          description
            "Counts the bytes transmitted on the PON port.";
        }
        leaf threshold-data-1-2-id {
          type omci-types:omci-uint16;
          description
            "Points to an instance of the threshold data 1 ME that contains PM threshold values.";
        }
      }
    }
    container PON_ONU_STATISTICS_STREAMING_ONU_GAL_ETHERNET_PM {
      description
        "PON_ONU_STATISTICS_STREAMING_ONU_GAL_ETHERNET_PM table in StateDB.";
      config false;
      list PON_ONU_STATISTICS_STREAMING_ONU_GAL_ETHERNET_PM_LIST {
        key "onu-name onu-id";
        description
          "GPON: Counters associated with gal ethernet messages.
           StateDB key: PON_ONU_STATISTICS_STREAMING_ONU_GAL_ETHERNET_PM|<onu-name>|<onu-id>.";
        leaf onu-name {
          type leafref {
            path "/sp:sonic-pon/sp:PON_ONU_STATE/sp:PON_ONU_STATE_LIST/sp:onu-name";
          }
          description
            "References PON_ONU_STATE_LIST.";
        }
        leaf onu-id {
          type uint16;
          description
            "Performance management ME ID.";
        }
        leaf discarded-downstream-frames {
          type uint64;
          description
            "Counts the number of downstream GEM frames discarded for any reason";
        }
        leaf discarded-upstream-frames {
          type uint64;
          description
            "Counts the number of upstream frames discarded prior to GEM encapsulation (due to congestion)";
        }
        leaf interval-end-time {
          type uint64;
          description
            "Identifies the most recently finished 15 min interval";
        }
        leaf threshold-data-1-2-id {
          type omci-types:omci-uint16;
          description
            "Points to an instance of the threshold data 1 ME that contains PM threshold values";
        }
      }
    }
    container PON_ONU_STATISTICS_STREAMING_ONU_GEM_PORT_NETWORK_CTP_PM {
      description
        "PON_ONU_STATISTICS_STREAMING_ONU_GEM_PORT_NETWORK_CTP_PM table in StateDB.";
      config false;
      list PON_ONU_STATISTICS_STREAMING_ONU_GEM_PORT_NETWORK_CTP_PM_LIST {
        key "onu-name onu-id";
        description
          "GPON: Counters associated with gem port network ctp messages.
           StateDB key: PON_ONU_STATISTICS_STREAMING_ONU_GEM_PORT_NETWORK_CTP_PM|<onu-name>|<onu-id>.";
        leaf onu-name {
          type leafref {
            path "/sp:sonic-pon/sp:PON_ONU_STATE/sp:PON_ONU_STATE_LIST/sp:onu-name";
          }
          description
            "References PON_ONU_STATE_LIST.";
        }
        leaf onu-id {
          type uint16;
          description
            "Performance management ME ID.";
        }
        leaf encryption-key-errors {
          type uint64;
          description
            "Counts GEM frames with erroneous encryption key indexes. If the GEM port is not encrypted,
             this attribute counts any frame with a key index not equal to 0. If the GEM port is encrypted,
             this attribute counts any frame whose key index specifies a key that is not known to the ONU.
            ";
        }
        leaf interval-end-time {
          type uint64;
          description
            "Identifies the most recently finished 15 min interval";
        }
        leaf received-gem-frames {
          type uint64;
          description
            "Counts GEM frames received correctly on the monitored GEM port. A correctly received GEM frame
             is one that does not contain uncorrectable errors and has a valid header error check (HEC).
            ";
        }
        leaf received-payload-bytes {
          type uint64;
          description
            "Counts user payload bytes received on the monitored GEM port";
        }
        leaf threshold-data-1-2-id {
          type omci-types:omci-uint16;
          description
            "Points to an instance of the threshold data 1 ME that contains PM threshold values";
        }
        leaf transmitted-gem-frames {
          type uint64;
          description
            "Counts GEM frames transmitted on the monitored GEM port";
        }
        leaf transmitted-payload-bytes {
          type uint64;
          description
            "Counts user payload bytes transmitted on the monitored GEM port";
        }
      }
    }
    container PON_ONU_STATISTICS_STREAMING_ONU_ENHANCED_TC_PM {
      description
        "PON_ONU_STATISTICS_STREAMING_ONU_ENHANCED_TC_PM table in StateDB.";
      config false;
      list PON_ONU_STATISTICS_STREAMING_ONU_ENHANCED_TC_PM_LIST {
        key "onu-name onu-id";
        description
          "GPON: Enhanced TC statistics reported by ONU.
           StateDB key: PON_ONU_STATISTICS_STREAMING_ONU_ENHANCED_TC_PM|<onu-name>|<onu-id>.";
        leaf onu-name {
          type leafref {
            path "/sp:sonic-pon/sp:PON_ONU_STATE/sp:PON_ONU_STATE_LIST/sp:onu-name";
          }
          description
            "References PON_ONU_STATE_LIST.";
        }
        leaf onu-id {
          type uint16;
          description
            "ME Identifier for this TC.";
        }
        leaf lods-event-count {
          type uint64;
          description
            "Counts the number of state transitions from O5.1 to O6";
        }
        leaf lods-event-restored-count {
          type uint64;
          description
            "Counts the number of LODS cleared events";
        }
        leaf fragment-xgem-frames {
          type uint64;
          description
            "Counts the number of XGEM frames that represent fragmented SDUs, as indicated by the LF bit = 0";
        }
        leaf interval-end-time {
          type uint64;
          description
            "Identifies the most recently finished 15 min interval";
        }
        leaf onu-reactivation-by-lods-events {
          type uint64;
          description
            "Counts the number of LODS events resulting in ONU reactivation without synchronization being reacquired";
        }
        leaf psbd-hec-error-count {
          type uint64;
          description
            "Counts HEC errors in any of the fields of the downstream physical sync block";
        }
        leaf received-bytes-in-nonidle-xgem-frames {
          type uint64;
          description
            "Counts the number of received bytes in non-idle XGEM frames";
        }
        leaf transmitted-bytes-in-nonidle-xgem-frames {
          type uint64;
          description
            "Counts the number of transmitted bytes in non-idle XGEM frames";
        }
        leaf transmitted-xgem-frames {
          type uint64;
          description
            "Counts the number of non-idle XGEM frames transmitted. If an SDU is fragmented, each fragment is an XGEM frame and is counted as such.";
        }
        leaf unknown-profile-count {
          type uint64;
          description
            "Counts the number of grants received whose specified profile was not known to the ONU";
        }
        leaf xgem-hec-lost-words-count {
          type uint64;
          description
            "Counts the number of 4 byte words lost because of an XGEM frame HEC error. In general, all XGTC
             payload following the error is lost, until the next PSBd event.
            ";
        }
        leaf xgem-key-errors {
          type uint64;
          description
            "Counts the number of downstream XGEM frames received with an invalid key specification";
        }
        leaf xgem-hec-error-count {
          type uint64;
          description
            "Counts the number of instances of an XGEM frame HEC error";
        }
        leaf xgtc-hec-error-count {
          type uint64;
          description
            "Counts HEC errors detected in the XGTC header";
        }
        leaf threshold-data-64-bit-id {
          type uint64;
          description
            "Points to an instance of the threshold data 1 ME that contains PM threshold values";
        }
      }
    }
    container PON_ONU_STATISTICS_STREAMING_ONU_XG_PON_DOWNSTREAM_MGMT_PM {
      description
        "PON_ONU_STATISTICS_STREAMING_ONU_XG_PON_DOWNSTREAM_MGMT_PM table in StateDB.";
      config false;
      list PON_ONU_STATISTICS_STREAMING_ONU_XG_PON_DOWNSTREAM_MGMT_PM_LIST {
        key "onu-name onu-id";
        description
          "GPON: Counters associated with downstream PLOAM and OMCI messages.
           StateDB key: PON_ONU_STATISTICS_STREAMING_ONU_XG_PON_DOWNSTREAM_MGMT_PM|<onu-name>|<onu-id>.";
        leaf onu-name {
          type leafref {
            path "/sp:sonic-pon/sp:PON_ONU_STATE/sp:PON_ONU_STATE_LIST/sp:onu-name";
          }
          description
            "References PON_ONU_STATE_LIST.";
        }
        leaf onu-id {
          type uint16;
          description
            "Performance management ME ID.";
        }
        leaf interval-end-time {
          type uint64;
          description
            "Identifies the most recently finished 15 min interval.";
        }
        leaf threshold-data-1-2-id {
          type omci-types:omci-uint16;
          description
            "Points to an instance of the threshold data 1 ME that contains PM threshold values.";
        }
        leaf ploam-mic-error-count {
          type uint64;
          description
            "Counts MIC errors detected in downstream PLOAM messages, either directed to this ONU or broadcast to all ONUs";
        }
        leaf downstream-ploam-message-count {
          type uint64;
          description
            "Counts PLOAM messages received, either directed to this ONU or broadcast to all ONUs";
        }
        leaf profile-messages-received {
          type uint64;
          description
            "Counts the number of profile messages received, either directed to this ONU or broadcast to all ONUs.";
        }
        leaf ranging-time-messages-received {
          type uint64;
          description
            "Counts the number of ranging_time messages received, either directed to this ONU or broadcast to all ONUs.";
        }
        leaf deactivate-onu-id-messages-received {
          type uint64;
          description
            "Counts the number of deactivate_ONU-ID messages received, either directed to this ONU or broadcast to all ONUs";
        }
        leaf disable-serial-number-messages-received {
          type uint64;
          description
            "Counts the number of disable_serial_number messages received, whose serial number specified this ONU";
        }
        leaf request-registration-messages-received {
          type uint64;
          description
            "Counts the number of request_registration messages received";
        }
        leaf assign-alloc-id-messages-received {
          type uint64;
          description
            "Counts the number of assign_alloc-ID messages received";
        }
        leaf key-control-messages-received {
          type uint64;
          description
            "Counts the number of key_control messages received";
        }
        leaf sleep-allow-messages-received {
          type uint64;
          description
            "Counts the number of sleep_allow messages received";
        }
        leaf baseline-omci-messages-received-count {
          type uint64;
          description
            "Counts the number of OMCI messages received in the baseline message format";
        }
        leaf extended-omci-messages-received-count {
          type uint64;
          description
            "Counts the number of OMCI messages received in the extended message format";
        }
        leaf assign-onu-id-omci-messages-received {
          type uint64;
          description
            "Counts the number of assign_ONU-ID messages received since the last reboot";
        }
        leaf omci-mic-error-count {
          type uint64;
          description
            "Counts the number of MIC errors detected in OMCI messages directed to this ONU";
        }
      }
    }
    container PON_ONU_STATISTICS_STREAMING_ONU_XG_PON_UPSTREAM_MGMT_PM {
      description
        "PON_ONU_STATISTICS_STREAMING_ONU_XG_PON_UPSTREAM_MGMT_PM table in StateDB.";
      config false;
      list PON_ONU_STATISTICS_STREAMING_ONU_XG_PON_UPSTREAM_MGMT_PM_LIST {
        key "onu-name onu-id";
        description
          "GPON: Counters associated with upstream PLOAM and OMCI messages.
           StateDB key: PON_ONU_STATISTICS_STREAMING_ONU_XG_PON_UPSTREAM_MGMT_PM|<onu-name>|<onu-id>.";
        leaf onu-name {
          type leafref {
            path "/sp:sonic-pon/sp:PON_ONU_STATE/sp:PON_ONU_STATE_LIST/sp:onu-name";
          }
          description
            "References PON_ONU_STATE_LIST.";
        }
        leaf onu-id {
          type uint16;
          description
            "Performance management ME ID.";
        }
        leaf interval-end-time {
          type uint64;
          description
            "Identifies the most recently finished 15 min interval.";
        }
        leaf threshold-data-1-2-id {
          type omci-types:omci-uint16;
          description
            "Points to an instance of the threshold data 1 ME that contains PM threshold values.";
        }
        leaf upstream-ploam-message-count {
          type uint64;
          description
            "Counts PLOAM messages transmitted upstream, excluding acknowledge messages";
        }
        leaf serial-number-message-count {
          type uint64;
          description
            "Counts Serial_number_ONU PLOAM messages transmitted";
        }
        leaf registration-message-count {
          type uint64;
          description
            "Counts registration PLOAM messages transmitted";
        }
        leaf key-report-message-count {
          type uint64;
          description
            "Counts key_report PLOAM messages transmitted";
        }
        leaf acknowledge-message-count {
          type uint64;
          description
            "Counts acknowledge PLOAM messages transmitted. It includes all forms of acknowledgement,
             including those transmitted in response to a PLOAMu grant when the ONU has nothing to send.
            ";
        }
        leaf sleep-request-message-count {
          type uint64;
          description
            "Counts sleep_request PLOAM messages transmitted";
        }
      }
    }
    container PON_ONU_STATISTICS_STREAMING_ONU_FEC_PM {
      description
        "PON_ONU_STATISTICS_STREAMING_ONU_FEC_PM table in StateDB.";
      config false;
      list PON_ONU_STATISTICS_STREAMING_ONU_FEC_PM_LIST {
        key "onu-name onu-id";
        description
          "GPON: FEC statistics reported by ONU through OMCI.
           StateDB key: PON_ONU_STATISTICS_STREAMING_ONU_FEC_PM|<onu-name>|<onu-id>.";
        leaf onu-name {
          type leafref {
            path "/sp:sonic-pon/sp:PON_ONU_STATE/sp:PON_ONU_STATE_LIST/sp:onu-name";
          }
          description
            "References PON_ONU_STATE_LIST.";
        }
        leaf onu-id {
          type uint16;
          description
            "Performance management ME ID.";
        }
        leaf corrected-bytes {
          type uint64;
          description
            "corrected bytes";
        }
        leaf corrected-code-words {
          type uint64;
          description
            "corrected code words";
        }
        leaf fec-seconds {
          type uint64;
          description
            "fec seconds";
        }
        leaf interval-end-time {
          type uint64;
          description
            "interval end time";
        }
        leaf threshold-data-1-2-id {
          type omci-types:omci-uint16;
          description
            "threshold data 1/2 id";
        }
        leaf total-code-words {
          type uint64;
          description
            "total code words";
        }
        leaf uncorrectable-code-words {
          type uint64;
          description
            "uncorrectable code words";
        }
      }
    }
    container PON_FIRMWARE_FILENAME_STATE {
      description
        "PON_FIRMWARE_FILENAME_STATE table in StateDB.";
      config false;
      list PON_FIRMWARE_FILENAME_STATE_LIST {
        key "filename";
        description
          "PON_FIRMWARE_FILENAME_STATE configuration.
           StateDB key: PON_FIRMWARE_FILENAME_STATE|<filename>.";
        leaf filename {
          type string;
        }
      }
    }
    container PON_OLT_PLUG_STATE {
      description
        "PON_OLT_PLUG_STATE table in StateDB.";
      config false;
      list PON_OLT_PLUG_STATE_LIST {
        key "name";
        description
          "List of OLT plug state entries.
           StateDB key: PON_OLT_PLUG_STATE|<name>.";
        leaf name {
          type leafref {
            path "/sp:sonic-pon/sp:PON_OLT_INTF_STATE/sp:PON_OLT_INTF_STATE_LIST/sp:olt-intf-name";
          }
          description
            "References PON_OLT_INTF_STATE_LIST.";
        }
        leaf fw-bank-ptr {
          type uint16;
          description
            "Current Firmware bank pointer";
        }
        leaf fw-version {
          type string;
          description
            "The current running version of firmware";
        }
        leaf hardware-version {
          type string;
          description
            "OLT module hardware revision.";
        }
        leaf manufacturer {
          type string;
          description
            "Manufacturer of the module.";
        }
        leaf manufacturer-model {
          type string;
          description
            "Manufacturer model of the module.";
        }
        leaf manufacturer-serial-number {
          type string;
          description
            "OLT subassembly serial number.";
        }
        leaf model {
          type string;
          description
            "Manufacturer Model Name.";
        }
        leaf online-time {
          type yang:date-and-time;
          description
            "The last time the Controller successfully completed configuration of the OLT.";
        }
        leaf production-code {
          type string;
          description
            "Device production code.";
        }
        leaf serial-number {
          type string;
          description
            "The serial number for the Module. This value is assigned by the vendor of the OLT module and is often OLT-<MAC Address>.";
        }
        leaf uptime {
          type uint64;
          units "milliseconds";
          description
            "The time since the OLT module was reset.";
        }
        leaf switch-chassis-id {
          type string;
          description
            "MAC address of switch.";
        }
        leaf switch-ipv4-address {
          type string;
          description
            "IP Address of the switch.";
        }
        leaf switch-ipv6-address {
          type string;
          description
            "IP Address of the switch.";
        }
        leaf switch-port-description {
          type string;
          description
            "String description of the port";
        }
        leaf switch-port-id {
          type string;
          description
            "String identification for the port.";
        }
        leaf switch-system-description {
          type string;
          description
            "System Description.";
        }
        leaf switch-system-name {
          type string;
          description
            "Name for the Switch.";
        }
        leaf fw-upgrade-bank {
          type uint16;
          description
            "Last firmware bank number (software download ME ID) firmware was downloaded to.";
        }
        leaf fw-upgrade-fx-code {
          type uint32;
          description
            "OLT plug Software Download error code.";
        }
        leaf fw-upgrade-file {
          type string;
          description
            "Name of the file to download.";
        }
        leaf fw-upgrade-status {
          type string;
          description
            "Software download status (Downloading, Success, Failed).";
        }
        leaf fw-upgrade-duration {
          type string;
          description
            "Length of time in hours, minutes, and seconds for the OLT plug upgrade to complete.";
        }
        leaf fw-upgrade-time {
          type yang:date-and-time;
          description
            "Timestamp reporting time the OLT plug was upgraded.";
        }
        leaf hw-failure {
          type string;
          description
            "Current hardware failure status.";
        }
      }
    }
  }
}
